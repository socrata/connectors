FME workspace socrata_geospatial_publisher.fmwt
Title: socrata_geospatial_writer
Description: Use this to publish geospatial data from FME (FME geometry) to update a Socrata GeoSpatial (Mondara) dataset.
Shutdown Python:
      import urllib2
      import urllib
      import json
      import base64
      import fme
      import os.path
      import shutil

      import mimetools
      import mimetypes

      CRLF = '\r\n'
      BOUNDARY = mimetools.choose_boundary()

      # Get config from the environment
      username = fme.macroValues['socrata_username']
      password = fme.macroValues['socrata_password']
      app_token = 'Eu1EiCmxZN4DWT9UmiXCLQpl6' # same as that used by FME Socrata Writer
      uid = fme.macroValues['socrata_dataset_uid']
      domain = fme.macroValues['socrata_domain']

      path_to_geospatial_file = fme.macroValues['temp_shapefile']

      scan_url = "https://" + domain + "/api/imports2?"
      import_url = "https://" + domain + "/api/imports2?"

      geospatial_file_extension = os.path.splitext(path_to_geospatial_file)[1]
      if geospatial_file_extension != '.zip':
          raise Exception("ERROR: output_shapefile must have a .zip extension! Given file path '" + path_to_geospatial_file + "' is invalid." )


      def scanShapeFile(shapeFileName):
        with open(shapeFileName, 'rb') as geo_file:
          payload = geo_file.read()

        scan_params = {
          "method": "scanShape",
        }

        url = scan_url + urllib.urlencode(scan_params)
        mime_type = mimetypes.guess_type(shapeFileName)[0] or 'application/octet-stream'

        multipartFileParams = [("whatever", "test.zip", payload)]
        multipartData = EncodeMultiPart(multipartFileParams)
        multipartDataLength = len(multipartData)

        headers = {
          "X-App-Token" : app_token,
          "Authorization" : "Basic %s" % base64.encodestring("%s:%s" % (username, password)).replace('\n', ''),
          "Accept": "application/json",
          "Content-Type" : 'multipart/form-data;boundary=%s' % BOUNDARY,
          "Content-Length" : multipartDataLength
        }

        response = ""

        try:
          request = urllib2.Request(url, data = multipartData, headers = headers)
          request.get_method = lambda: 'POST'
          response = urllib2.urlopen(request)
          # print "Results: %s" % response.read()
          return json.load(response)
        except urllib2.HTTPError as e:
          # TODO: Smart error handling and stuff
          print "Code: %s" % e.code
          print "Error: %s" % e.read()


      def resplaceWithShapeScanResults(dataset_id, scan_result, shapeFileName):
        response = scan_result
        response_summary = response['summary']

        blueprint = {
          'layers': [
            {
              'layerId': layer['layerId'],
              'name': layer['name']
            } for layer in response_summary['layers']]
        }

        print "Sanitized Blueprint: \n" + json.dumps(blueprint)

        import_params = {
          "method": 'replaceShapefile',
          "fileId": response['fileId'],
          "name": shapeFileName,
          "blueprint": json.dumps(blueprint),
          "viewUid": dataset_id
        }

        payload = "";
        with open(shapeFileName, 'rb') as geo_file:
          payload = geo_file.read()

        multipartFileParams = [("whatever", shapeFileName, payload)]
        multipartData = EncodeMultiPart(multipartFileParams)

        headers = {
          "X-App-Token" : app_token,
          "Authorization" : "Basic %s" % base64.encodestring("%s:%s" % (username, password)).replace('\n', ''),
          "Accept": "application/json",
          "Content-Type" : 'multipart/form-data;boundary=%s' % BOUNDARY,
          "Content-Length" : len(multipartData)
        }

        try:
          request_url = import_url + urllib.urlencode(import_params) + "&$$version=2.0"
          print request_url
          request = urllib2.Request(request_url,
            data = multipartData, headers = headers)
          request.get_method = lambda: 'POST'
          response = urllib2.urlopen(request)
          return response.read()
        except urllib2.HTTPError as e:
          # TODO: Smart error handling and stuff
          print "Code: %s" % e.code
          print "Error: %s" % e.read()

      # modified from https://developers.google.com/cloud-print/docs/pythonCode
      def EncodeMultiPart(files, file_type='application/octet-stream'):
          """Encodes list of parameters and files for HTTP multipart format.

          Args:
            files: list of tuples containing param name, filename, and file contents.
            file_type: string if file type different than application/xml.
          Returns:
            A string to be sent as data for the HTTP post request.
          """
          lines = []
          for (key, filename, value) in files:
            lines.append('--' + BOUNDARY)
            lines.append(
                'Content-Disposition: form-data; name="%s"; filename="%s"'
                % (key, filename))
            lines.append('Content-Type: %s' % file_type)
            lines.append('')  # blank line
            lines.append(value)
          lines.append('--' + BOUNDARY + '--')
          lines.append('')  # blank line
          return CRLF.join(lines)




      ## actually perform the update
      result = scanShapeFile(path_to_geospatial_file)

      dataset = resplaceWithShapeScanResults(uid, result, path_to_geospatial_file)

      ## delete temp shapefile and directory
      temp_dir = os.path.dirname(os.path.realpath(fme.macroValues['temp_shapefile']))
      print "TEMP PATH: " + temp_dir
      shutil.rmtree(temp_dir)

Parameters:
- socrata_username = user@domain.com   # Username
- socrata_dataset_uid = mw25-9puy   # Dataset ID
- socrata_domain = your.domain.org   # Domain
- DestDataset_SHAPE = $(temp_shapefile)   # Destination Esri Shape Folder
- SourceDataset_SHAPE_2 = $(FME_MF_DIR)1/facilities/facilities.shp   # Source Esri Shape File(s)
- socrata_password = PASS   # Password
- temp_shapefile:   # Python Script
      import os
      import tempfile
      
      temp_dir = tempfile.mkdtemp()
      print "TEMP SHAPEFILE: " + temp_dir + '/shapefile_temp.zip'
      return temp_dir + '/shapefile_temp.zip'

Readers:
- SHAPE_1: SHAPE

Writers:
- SHAPE_2: SHAPE to $(DestDataset_SHAPE)

Note: Reads in Shapefile containing / a set of points representing / facilities in Austin, TX / You can replace this / with any FME Reader / that reads geospatial data
facilities (reader SHAPE_1)
    attributes: SDE_FACILI number(19,8), PERIMETER number(19,8), FAC_ number(19,8), FAC_ID number(19,8), ADDRESS char(40), NAME char(40), FACILITY char(50), D_OCT92_ number(19,8), D_OCT92_ID number(19,8), D_OCT92_S char(1), TYPE number(5,0), SECTORS_ char(16), JURIS_ char(16)
    -> facilities (writer SHAPE_2)
Note: Writes point data along with a subset of / attributes (7 of 13) from original source Shapefile. / NOTE: if you are publishing non-point data you / must change the "Allowed Geometries' as / appropriate.
Note: Don't forget to set these User Parameters: / socrata_username / socrata_password / socrata_dataset_uid (existing Socrata GeoSpatial dataset to update) / socrata_domain
facilities (writer SHAPE_2)
    attributes: SDE_FACILI number(19,8), PERIMETER number(19,8), FAC_ID number(19,8), ADDRESS char(40), NAME char(40), FACILITY char(50), TYPE number(5,0)

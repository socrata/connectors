FME workspace Shapefile2Socrata.fmwt
Title: Shapefile2Socrata

Parameters:
- SourceDataset_SHAPE = $(FME_MF_DIR)1/Inbox/tl_2013_us_county.zip   # Source Esri Shape File(s)
- socrata_username =   # Socrata Username
- socrata_app_token = nUDmWszBG05TG2Z1OingWe65A   # App Token
- socrata_batch_size = 1000   # Batch Size
- socrata_dataset_uid =   # Dataset UID
- socrata_domain =   # Domain of the Dataset
- DestDataset_SOCRATA = soda.demo.socrata.com   # Host

Readers:
- SHAPE_1: SHAPE from $(SourceDataset_SHAPE)

Writers:
- SOCRATA_1: SOCRATA to $(DestDataset_SOCRATA)

tl_2013_us_county (reader SHAPE_1)
    attributes: STATEFP char(2), COUNTYFP char(3), COUNTYNS char(8), GEOID char(5), NAME char(100), NAMELSAD char(100), LSAD char(2), CLASSFP char(2), MTFCC char(5), CSAFP char(3), CBSAFP char(5), METDIVFP char(5), FUNCSTAT char(1), ALAND number(14,0), AWATER number(14,0), INTPTLAT char(11), INTPTLON char(12)
    -> GeometryFilter
Note: Filter out non-point features
GeometryFilter
    GEOM_PORT_NAMES = Point
    BREAK_AGG = No
    <UNFILTERED> -> Invalid_Feature_Logger
    POINT -> Reprojector
Note: The writer will reproject to EPSG:4326 by default, / this ensures features are in the correct projection / before entering the writer.
Reprojector
    DEST = LL-WGS84
    RASTER_CELL_SIZE = Preserve Cells
    STROKE_ARCS = Yes
    SOURCE = Read from feature
    INTERPOLATION_TYPE_NAME = Nearest Neighbor
    REPROJECTED -> UserTable (writer SOCRATA_1)
Note: Generate a friendly error log / when a non-point feature enteres the pipeline
Invalid_Feature_Logger: Logger
    MESSAGE = The Socrata Writer only supports point features.
    MAXFEATS = 20
    MAXCOORDS = 20
    LOGGED -> UserTable (writer SOCRATA_1)
UserTable (writer SOCRATA_1)
InsidePointReplacer

Bookmark: Esri Shapefile Reader
Note: The Esri Shapefile Reader / 1. This is just a generic shapefile reader with one important note, Socrata currently only supports point features. Any other geometry type will get coerced down to its representative point feature. / 2. Be sure to update the attributes for your shapefile.

Bookmark: Point Replacer
Note: Insert the InsidePointReplacer for a little more control on how the writer converts your geometry

Bookmark: Socrata Writer
Note: The Socrata Writer needs the following parameters / - Socrata User Name (usually in the form of an email / - Socrata Password / - Data Set. Try: soda.demo.socrata.com / Be sure to copy the attributes from the data source in order to have the fields in Socrata. / Tip: You can save your self a bit of time by formatting the column types in the writer / Geometry features will populate a location column in Socrata that you will see when creating a map vizualization of the data.

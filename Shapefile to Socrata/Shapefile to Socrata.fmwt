FME workspace Shapefile to Socrata.fmwt
Title: shape2none

Parameters:
- SourceDataset_SHAPE = $(FME_MF_DIR)1/Inbox/tl_2013_us_county.zip   # Source Esri Shape File(s)
- socrata_username =   # Socrata Username
- socrata_app_token = nUDmWszBG05TG2Z1OingWe65A   # App Token
- socrata_batch_size = 1000   # Batch Size
- socrata_dataset_uid =   # Dataset UID
- socrata_domain =   # Domain of the Dataset
- socrata_password =   # Socrata Password

Readers:
- SHAPE_1: SHAPE from $(SourceDataset_SHAPE)

tl_2013_us_county (reader SHAPE_1)
    attributes: STATEFP char(2), COUNTYFP char(3), COUNTYNS char(8), GEOID char(5), NAME char(100), NAMELSAD char(100), LSAD char(2), CLASSFP char(2), MTFCC char(5), CSAFP char(3), CBSAFP char(5), METDIVFP char(5), FUNCSTAT char(1), ALAND number(14,0), AWATER number(14,0), INTPTLAT char(11), INTPTLON char(12)
    -> CenterOfGravityReplacer
CenterOfGravityReplacer
    CENTEROFGRAVITY -> BulkAttributeRenamer
BulkAttributeRenamer
    CASE_CHANGE_TYPE = lowercase
    ATTRCHOICE = All Attributes
    PATTERN_ACTION_DISP = Change Case
    -> SocrataWriter_v0.3
SocrataWriter_v0.3: PythonCaller
    PYTHONSOURCE:
      import fmeobjects
      import json
      import urllib2
      import base64

      class SocrataFeatureProcessor(object):
          def __init__(self):
              # Get config from the environment
              self.username = FME_MacroValues['socrata_username']
              self.password = FME_MacroValues['socrata_password']
              self.app_token = FME_MacroValues['socrata_app_token']
              self.uid = FME_MacroValues['socrata_dataset_uid']
              self.domain = FME_MacroValues['socrata_domain']
              self.batch_size = FME_MacroValues['socrata_batch_size']

              self.logger = fmeobjects.FMELogFile()
              self.records = []

              # Fetch some metadata about the dataset that we'll use later
              response = urllib2.urlopen(urllib2.Request("https://%s/resource/%s.json?$limit=1" % (self.domain, self.uid)))

              columns = json.loads(response.info()["X-SODA2-Fields"])
              datatypes = json.loads(response.info()["X-SODA2-Types"])

              self.schema = {}
              for i in range(len(columns)):
                  if datatypes[i] != "meta_data":
                      self.schema[columns[i]] = datatypes[i]

          def input(self, feature):
              record = {}

              # Find properties for all of our attributes
              for name, datatype in self.schema.iteritems():
                  if datatype == "location":
                      record[name] = {
                          "longitude" : feature.getGeometry().getXYZ()[0],
                          "latitude" : feature.getGeometry().getXYZ()[1]
                      }
                  elif feature.getAttribute(name) != None:
                      record[name] = feature.getAttribute(name)

              self.records.append(record)

              if len(self.records) >= int(self.batch_size):
                  self.logger.logMessageString("Writing batch of size %d" % len(self.records))
                  self.write()
                  self.records = []

          def write(self):
              # Write this batch out
              payload = json.dumps(self.records) + " \n"
              headers = {
                  "X-App-Token" : self.app_token,
                  "Authorization" : "Basic %s" % base64.encodestring("%s:%s" % (self.username, self.password)).replace('\n', ''),
                  "Content-Type" : "application/json",
                  "Content-Length" : len(payload)
              }

              try:
                  request = urllib2.Request("https://%s/resource/%s.json" % (self.domain, self.uid), data = payload, headers = headers)
                  response = urllib2.urlopen(request)
                  self.logger.logMessageString("Results: %s" % response.read())
              except urllib2.HTTPError as e:
                  # TODO: Smart error handling and stuff
                  self.logger.logMessageString("Code: %s" % e.code)
                  self.logger.logMessageString("Error: %s" % e.read())



          def close(self):
              self.logger.logMessageString("Writing final batch of size %d" % len(self.records))
              self.write()
              self.logger.logMessageString("Done.")
    PYTHONSYMBOL = SocrataFeatureProcessor

FME workspace socrata_to_socrata.fmw
Title: socrata_filter_to_socrata
Description: Reads data from existing Socrata dataset, filters out some rows, and publishes to new Socrata dataset.

Parameters:
- SourceDataset_CSV = https://data.mo.gov/api/views/wu22-kvdm/rows.csv?accessType=DOWNLOAD   # Source CSV (CommaSeparatedValue) File(s)

Readers:
- CSV_1: CSV from $(SourceDataset_CSV)

Writers:
- SOCRATA_1: SOCRATA

Note: Reads all rows from this Socrata dataset: / https://data.mo.gov/Regulatory/Missouri-Wholesaler-Licenses/wu22-kvdm
CSV (reader CSV_1)
    attributes: PRIMARY LICENSE number(7,0), PRIMARY TYPE char(5), LICENSEE char(41), DBANAME char(41), STREET NUMBER char(7), STREET char(31), CITY char(18), STATE char(3), ZIPCODE number(10,0), COUNTY char(15), DISTRICT number(2,0), SUBDIST number(3,0), PHONE NUMBER number(11,0)
    -> AttributeFilter
Note: Filters out all records from the source dataset except / those where the 'CITY' column is 'KANSAS CITY'
AttributeFilter
    ATTR_VALUES = <EMPTY>,<MISSING>,<NULL>,<UNFILTERED>,KANSAS CITY
    ATTR_NAME = CITY
    KANSAS CITY -> Kansas only (writer SOCRATA_1)
Note: This will create a new dataset on the given Domain / (you can change target domain in the Navigator panel)
Kansas only (writer SOCRATA_1)
    attributes: PRIMARY LICENSE number, PRIMARY TYPE text, LICENSEE text, DBANAME text, STREET NUMBER text, STREET text, CITY text, STATE text, ZIPCODE number, COUNTY text, DISTRICT number, SUBDIST number, PHONE NUMBER number

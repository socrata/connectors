FME workspace Socrata_BLDS_Schema.fmwt
Title: Socrata_BLDS_Schema
Description: Using FME to Convert Permit Datasets to BLDS
This FME workspace uses your existing permit data and a customized schema map to convert your permit data into a Core Building & Land Development Specification (BLDS) dataset version 1.2.
It uses the following transformers to remap your data to BLDS standards
FeatureReader - Reads in your permit data (a Reader may also be used)
AttributeRenamer - Rename your existing attributes to match BLDS and create ones you may be missing.
AttributeKeeper - Removes attributes that are not required for BLDS
AttributeTrimmer - Remove whitespace that may be hidden in your data (spaces/returns at the beginning/end of your data so it writes to Socrata
AttributeCreator - Maps existing data to predetermined BLDS values in specified columns
DateFormatter - Converts date values into BLDS formatted dates based on the Date_Format parameter
StringReplacer - Removes dollar symbols from monetary attributes to make them numeric values
AttributeRounder - Rounds decimals to nearest value to create integers and match BLDS format
AttributeManager - Orders the attributes consistent with BLDS format
FeautreWriter - Writes your BLDS data to a csv file, alternatively you can use the built in Socrata Writer or a writer of your choice to another format.
Steps:
Update the BLDS_FME_Schema.csv to build your schema map by populating column A with the column names from your permit dataset that corresponds with the BLDS column names (column B). For more information on the BLDS format, visit the page to describe the Core Requirements.
Open FME_BLDS_Template.fmw in FME. You can also customize this workspace to manipulate your permit data before converting to BLDS.
Update the Parameters in the Navigator pane.
Dataset - update with your dataset’s four-by-four
Date_Format - update with the format that your dates are saved, see FME documentation of how to build the date format string
Output_Folder - set the folder that your output file will be saved
Use the FeatureReader transformer to direct the workspace to the Format and Dataset of your permit data. Alternatively, you can create a new Reader to read in your data, connect it to the AttributeRenamer transformer.
Import your BLDS schema by opening the AttributeRenamer and clicking Import
Select Format csv and navigate to the dataset BLDS_FME_Schema.csv then click Next
Select Import From Values then click Next.
Select the attributes to import by setting Old Attribute to Source_Attribute_Name and New Attribute to BLDS_Attribute then click Import.
Check that all of your attributes will be renamed appropriately.
Populate mapped fields with the AttributeCreator, these are fields within BLDS that must have standard values and have the suffix ‘Mapped’. These fields are recommended, not required. To see the valid values for this column visit the Core Requirements page. If your data is already mapped with standard values, you can skip this step and bypass the AttributeCreator transformer. If you do bypass the AttriubuteCreator then disable the transformer.
This step will require an understanding of your permit data to map the following fields in BLDS:
PermitClassMapped
StatusCurrentMapped
WorkClassMapped
PermitTypeMapped
ContractorTradeMapped
The five attributes in the AttributeCreator have their values set with Conditional Definitions, this allows FME to create attributes based on the idea of "If ThisValue = x, then ThatValue = y" and is dependent upon rules created by the user called Conditional Definitions. To open the Conditional Definition parameter for one attribute, double-click on the table icon in the Attribute Value column of the transformer.
The first line in this parameter will test for any null/missing/empty values to be a blank value in your output, do not edit this. Subsequent Test Conditions will be edited to map your existing data to mapped columns. You will not have to change the Output Values because these are the expected values for BLDS. Open a Test Condition by double-clicking one of the ‘Else If’ lines.
Within the Test Condition, you can set which values in your permit data will map to each BLDS value, here you will only need to update the Right Value of the test. Note: the Left Value converts the contents of your permit data to lower case to standardize the case. Only type Right Values in lowercase.
If more than one value in your permit data maps to a single value in the BLDS (e.g. House and Condo may both map to Residential) dataset, you can create more tests by selecting one of the tests and clicking Duplicate. For each additional Test Condition, edit the Right Value until you have accounted for all of the values in your permit data that will map the the BLDS value.
Complete the steps above for the remaining Output Values within the attribute to be mapped. Then move to the next attribute in the AttributeCreator until all of the Mapped attributes are populated. Then click OK.
If you want your BLDS data published to Socrata using FME, update the parameters in the Socrata writer and in the Navigator pane and enable the connection from the AttributeManager to the Socrata Writer. Otherwise, the FeatureWriter will create a csv of your BLDS data in the folder you specified in the Output_Folder parameter.
Run the workspace by clicking the green ‘play’ button near the top left menu.
Open the workspace output and check for any errors.
This workspace does not validate data for any errors, if check all values before publishing the data. Pay special attention to mapped values and dates.
Examine the date fields to check that the DateFormatter output your data into the format YYYY-MM-DD. If it did not, it’s likely an error in creating your Date_Format parameter.

Parameters:
- Dataset = 1234-abcd   # What is the dataset four-by-four?
- Date_Format = %m/%d/%Y   # What is the date format?
- Output_Folder = $(FME_MF_DIR_USERTYPED)   # What is the folder for your output?

Writers:
- SOCRATA_1: SOCRATA

Note: Author: Chris De Sisto / Company: Tyler Technologies (formerly Socrata) / E-mail: chris.desisto@tylertech.com / DevVersion: FME(R) 2018.1.0.0 (20180417 - Build 18459 - macosx) / Summary of workspace: / Maps values from an input file source to the BLDS schema. Complete documentation provided in Workspace Parameters > Description > Overview
Creator
    GEOMTYPE = Geometry Object
    NUM = 1
    CREATED -> FeatureReader [INITIATOR]
Note: Use the FeatureReader to point the workflow to your dataset or create a new reader and connect it to the AttributeReader after disconnecting this FeatureReader.
FeatureReader
    ATTRIBUTES = CSV,"permitnum,description,applieddate,issueddate,completeddate,statuscurrent,originaladdress1,originaladdress2,originalcity,originalstate,originalzip,jurisdiction,permitclass,permitclassmapped,statuscurrentmapped,workclass,workclassmapped,permittype,permittypemapped,permittypedesc,statusdate,totalsqft,link,latitude,longitude,estprojectcost,housingunits,pin,contractorcompanyname,contractortrade,contractortrademapped,contractorlicnum,contractorstatelic,proposeduse,addedsqft,removedsqft,masterpermitnum,expiresdate,coissueddate,holddate,voiddate,projectname,projectid,totalfinishedsqft,totalunfinishedsqft,totalheatedsqft,totalunheatedsqft,totalaccsqft,totalsprinkledsqft,extrafields,publisher,fee,contractorfullname,contractorcompanydesc,contractorphone,contractoraddress1,contractoraddress2,contractorcity,contractorstate,contractorzip,contractoremail"
    ATTR_ACCUM_MODE = Only Use Result
    COMBINE_GEOM = Use Result
    CSV_SCAN_MAX_FEATURES = 1000
    CSV__ALLOW_SPACES_IN_COLUMN_NAMES = yes
    CSV__DUPLICATE_DELIMS = no
    CSV__FIELD_NAMES_AFTER_HEADER = no
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES permitnum%description%applieddate%issueddate%completeddate%statuscurrent%originaladdress1%originaladdress2%originalcity%originalstate%originalzip%jurisdiction%permitclass%permitclassmapped%statuscurrentmapped%workclass%workclassmapped%permittype%permittypemapped%permittypedesc%statusdate%totalsqft%link%latitude%longitude%estprojectcost%housingunits%pin%contractorcompanyname%contractortrade%contractortrademapped%contractorlicnum%contractorstatelic%proposeduse%addedsqft%removedsqft%masterpermitnum%expiresdate%coissueddate%holddate%voiddate%projectname%projectid%totalfinishedsqft%totalunfinishedsqft%totalheatedsqft%totalunheatedsqft%totalaccsqft%totalsprinkledsqft%extrafields%publisher%fee%contractorfullname%contractorcompanydesc%contractorphone%contractoraddress1%contractoraddress2%contractorcity%contractorstate%contractorzip%contractoremail\"%%\"Filter\"%\"STRING_ENCODED _FILTER_REGEX \"%%\"Invert Filter\"%\"CHECKBOX _FILTER_UNMATCHED yes%no\"%no"
    CSV__GROUP_BY_DATASET = no
    CSV__IN_FIELD_NAMES = YES
    CSV__IN_SEPARATOR = ,
    CSV__SCHEMA = char,1,,char,1,,char,11,,char,1,,char,23,,char,1,,char,1,,char,1,,char,1,,char,1,,char,1,,char,1,,char,1,,char,1,,char,31,,char,1,,char,9,,char,1,,char,11,,char,1,,char,1,,char,1,,char,1,,char,1,,char,1,,char,1,,char,1,,char,1,,char,1,,char,1,,char,13,,char,1,,char,1,,char,1,,char,1,,char,1,,char,1,,char,1,,char,1,,char,1,,char,1,,char,1,,char,1,,char,1,,char,1,,char,1,,char,1,,char,1,,char,1,,char,1,,char,1,,char,6,,char,1,,char,1,,char,1,,char,1,,char,1,,char,1,,char,1,,char,1,,char,1,
    CSV__SCHEMA_WITH_COL_NAMES = permitnum,char,1,,description,char,1,,applieddate,char,11,,issueddate,char,1,,completeddate,char,23,,statuscurrent,char,1,,originaladdress1,char,1,,originaladdress2,char,1,,originalcity,char,1,,originalstate,char,1,,originalzip,char,1,,jurisdiction,char,1,,permitclass,char,1,,permitclassmapped,char,1,,statuscurrentmapped,char,31,,workclass,char,1,,workclassmapped,char,9,,permittype,char,1,,permittypemapped,char,11,,permittypedesc,char,1,,statusdate,char,1,,totalsqft,char,1,,link,char,1,,latitude,char,1,,longitude,char,1,,estprojectcost,char,1,,housingunits,char,1,,pin,char,1,,contractorcompanyname,char,1,,contractortrade,char,1,,contractortrademapped,char,13,,contractorlicnum,char,1,,contractorstatelic,char,1,,proposeduse,char,1,,addedsqft,char,1,,removedsqft,char,1,,masterpermitnum,char,1,,expiresdate,char,1,,coissueddate,char,1,,holddate,char,1,,voiddate,char,1,,projectname,char,1,,projectid,char,1,,totalfinishedsqft,char,1,,totalunfinishedsqft,char,1,,totalheatedsqft,char,1,,totalunheatedsqft,char,1,,totalaccsqft,char,1,,totalsprinkledsqft,char,1,,extrafields,char,1,,publisher,char,1,,fee,char,6,,contractorfullname,char,1,,contractorcompanydesc,char,1,,contractorphone,char,1,,contractoraddress1,char,1,,contractoraddress2,char,1,,contractorcity,char,1,,contractorstate,char,1,,contractorzip,char,1,,contractoremail,char,1,
    CSV__SKIP_FOOTER = 0
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES permitnum%description%applieddate%issueddate%completeddate%statuscurrent%originaladdress1%originaladdress2%originalcity%originalstate%originalzip%jurisdiction%permitclass%permitclassmapped%statuscurrentmapped%workclass%workclassmapped%permittype%permittypemapped%permittypedesc%statusdate%totalsqft%link%latitude%longitude%estprojectcost%housingunits%pin%contractorcompanyname%contractortrade%contractortrademapped%contractorlicnum%contractorstatelic%proposeduse%addedsqft%removedsqft%masterpermitnum%expiresdate%coissueddate%holddate%voiddate%projectname%projectid%totalfinishedsqft%totalunfinishedsqft%totalheatedsqft%totalunheatedsqft%totalaccsqft%totalsprinkledsqft%extrafields%publisher%fee%contractorfullname%contractorcompanydesc%contractorphone%contractoraddress1%contractoraddress2%contractorcity%contractorstate%contractorzip%contractoremail\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__STRIP_QUOTES = yes
    DATASET = $(FME_MF_DIR_USERTYPED)/BLDS_Attribtues_Ordered.csv
    FEATURETYPES = CSV
    FORMAT = CSV
    OUTPUT_FEATURES_DISPLAY = Schema and Data Features
    CSV -> AttributeRenamer
Note: Import old/new attributes here to rename attributes to match BLDS format
Note: DO NOT UPGRADE THIS TRANSFORMER, V3 HAS FUNCTIONALITY THAT V4 DOES NOT HAVE
AttributeRenamer
    ATTR_LIST = ,AddedSqFt,,,AppliedDate,,,COIssuedDate,,,CompletedDate,,,ContractorAddress1,,,ContractorAddress2,,,ContractorCity,,,ContractorCompanyDesc,,,ContractorCompanyName,,,ContractorEmail,,,ContractorFullName,,,ContractorLicNum,,,ContractorPhone,,,ContractorState,,,ContractorStateLic,,,ContractorTrade,,,ContractorTradeMapped,,,ContractorZip,,,Description,,,EstProjectCost,,,ExpiresDate,,,ExtraFields,,,Fee,,,HoldDate,,,HousingUnits,,,IssuedDate,,,Jurisdiction,,,Latitude,,,Link,,,Longitude,,,MasterPermitNum,,,OriginalAddress1,,,OriginalAddress2,,,OriginalCity,,,OriginalState,,,OriginalZip,,,PIN,,,PermitClass,,,PermitClassMapped,,,PermitNum,,,PermitType,,,PermitTypeDesc,,,PermitTypeMapped,,,ProjectID,,,ProjectName,,,ProposedUse,,,Publisher,,,RemovedSqFt,,,StatusCurrent,,,StatusCurrentMapped,,,StatusDate,,,TotalAccSqFt,,,TotalFinishedSqFt,,,TotalHeatedSqFt,,,TotalSprinkledSqFt,,,TotalSqFt,,,TotalUnHeatedSqFt,,,TotalUnfinishedSqFt,,,VoidDate,,,WorkClass,,,WorkClassMapped,
    -> AttributeKeeper
Note: Keeps only attributes needed for Core BLDS dataset
AttributeKeeper
    KEEP_ATTRS = ContractorStateLic,PermitTypeDesc,StatusDate,Description,Longitude,ContractorEmail,ContractorState,Jurisdiction,ProjectID,RemovedSqFt,PermitType,IssuedDate,VoidDate,ContractorZip,TotalHeatedSqFt,TotalSqFt,ContractorTrade,PermitTypeMapped,ContractorLicNum,ContractorCity,PermitNum,Publisher,ContractorFullName,ExtraFields,OriginalCity,WorkClass,ContractorCompanyDesc,Fee,OriginalState,CompletedDate,ExpiresDate,ProjectName,OriginalZip,PermitClass,TotalAccSqFt,COIssuedDate,PIN,AppliedDate,HoldDate,ContractorAddress1,ContractorAddress2,ContractorPhone,ContractorTradeMapped,HousingUnits,StatusCurrentMapped,EstProjectCost,TotalFinishedSqFt,ContractorCompanyName,TotalSprinkledSqFt,OriginalAddress1,Link,OriginalAddress2,TotalUnHeatedSqFt,Latitude,StatusCurrent,PermitClassMapped,WorkClassMapped,AddedSqFt,ProposedUse,TotalUnfinishedSqFt,MasterPermitNum
    -> AttributeTrimmer
Note: Trims whitespace from beginning & end of feature
AttributeTrimmer
    SRC_ATTRS = ContractorStateLic,PermitTypeDesc,StatusDate,Description,Longitude,ContractorEmail,ContractorState,Jurisdiction,ProjectID,RemovedSqFt,PermitType,IssuedDate,VoidDate,ContractorZip,TotalHeatedSqFt,TotalSqFt,ContractorTrade,PermitTypeMapped,ContractorLicNum,ContractorCity,PermitNum,Publisher,ContractorFullName,ExtraFields,OriginalCity,WorkClass,ContractorCompanyDesc,Fee,OriginalState,CompletedDate,ExpiresDate,ProjectName,OriginalZip,PermitClass,TotalAccSqFt,COIssuedDate,PIN,AppliedDate,HoldDate,ContractorAddress1,ContractorAddress2,ContractorPhone,ContractorTradeMapped,HousingUnits,StatusCurrentMapped,EstProjectCost,TotalFinishedSqFt,ContractorCompanyName,TotalSprinkledSqFt,OriginalAddress1,Link,OriginalAddress2,TotalUnHeatedSqFt,Latitude,StatusCurrent,WorkClassMapped,AddedSqFt,ProposedUse,TotalUnfinishedSqFt,MasterPermitNum
    TRIM_TO_NONE = Yes
    TRIM_TYPE = Both
    -> AttributeCreator
Note: Use this AttributeCreator to map your existing values to BLDS standard values. / BYPASS THIS TRANSFORMER IF YOUR VALUES ARE ALREADY MAPPED TO BLDS STANDARDS
AttributeCreator
    ATTR_TABLE:
      SET_TO PermitClassMapped = FME_CONDITIONAL:DEFAULT_VALUE''BOOL_OP;OR;COMPOSITE_TEST;<Unused>;TEST PermitClass ATTRIBUTE_VALUE_NULL _FME_BLANK_STRING_;TEST PermitClass ATTRIBUTE_IS_EMPTY _FME_BLANK_STRING_;TEST PermitClass ATTRIBUTE_IS_MISSING _FME_BLANK_STRING_''BOOL_OP;OR;COMPOSITE_TEST;<Unused>;TEST @LowerCase(@Value(PermitClass)) CONTAINS residential'Residential'BOOL_OP;OR;COMPOSITE_TEST;<Unused>;TEST @LowerCase(@Value(PermitClass)) CONTAINS commercial'Non-Residential'FME_NUM_CONDITIONS4___
      SET_TO StatusCurrentMapped = FME_CONDITIONAL:DEFAULT_VALUE''BOOL_OP;OR;COMPOSITE_TEST;<Unused>;TEST StatusCurrent ATTRIBUTE_VALUE_NULL _FME_BLANK_STRING_;TEST StatusCurrent ATTRIBUTE_IS_EMPTY _FME_BLANK_STRING_;TEST StatusCurrent ATTRIBUTE_IS_MISSING _FME_BLANK_STRING_''BOOL_OP;OR;COMPOSITE_TEST;<Unused>;TEST @LowerCase(@Value(StatusCurrent)) CONTAINS application accepted'Application Accepted'BOOL_OP;OR;COMPOSITE_TEST;<Unused>;TEST @LowerCase(@Value(StatusCurrent)) CONTAINS fees/payment'Fees/Payment'BOOL_OP;OR;COMPOSITE_TEST;<Unused>;TEST @LowerCase(@Value(StatusCurrent)) CONTAINS in review'In Review'BOOL_OP;OR;COMPOSITE_TEST;<Unused>;TEST @LowerCase(@Value(StatusCurrent)) CONTAINS permit issued'Permit Issued'BOOL_OP;OR;COMPOSITE_TEST;<Unused>;TEST @LowerCase(@Value(StatusCurrent)) CONTAINS inspection phase'Inspection Phase'BOOL_OP;OR;COMPOSITE_TEST;<Unused>;TEST @LowerCase(@Value(StatusCurrent)) CONTAINS permit finaled'Permit Finaled'BOOL_OP;OR;COMPOSITE_TEST;<Unused>;TEST @LowerCase(@Value(StatusCurrent)) CONTAINS permit finaled with conditions'Permit Finaled with Conditions'BOOL_OP;OR;COMPOSITE_TEST;<Unused>;TEST @LowerCase(@Value(StatusCurrent)) CONTAINS occupancy'Occupancy'BOOL_OP;OR;COMPOSITE_TEST;<Unused>;TEST @LowerCase(@Value(StatusCurrent)) CONTAINS appeal'Appeal'BOOL_OP;OR;COMPOSITE_TEST;<Unused>;TEST @LowerCase(@Value(StatusCurrent)) CONTAINS permit cancelled'Permit Cancelled'FME_NUM_CONDITIONS12___
      SET_TO WorkClassMapped = FME_CONDITIONAL:DEFAULT_VALUE'Existing'BOOL_OP;OR;COMPOSITE_TEST;<Unused>;TEST WorkClass ATTRIBUTE_VALUE_NULL _FME_BLANK_STRING_;TEST WorkClass ATTRIBUTE_IS_EMPTY _FME_BLANK_STRING_;TEST WorkClass ATTRIBUTE_IS_MISSING _FME_BLANK_STRING_''BOOL_OP;OR;COMPOSITE_TEST;<Unused>;TEST @LowerCase(@Value(WorkClass)) CONTAINS new'New'FME_NUM_CONDITIONS3___
      SET_TO PermitTypeMapped = FME_CONDITIONAL:DEFAULT_VALUE''BOOL_OP;OR;COMPOSITE_TEST;<Unused>;TEST PermitType ATTRIBUTE_VALUE_NULL _FME_BLANK_STRING_;TEST PermitType ATTRIBUTE_IS_EMPTY _FME_BLANK_STRING_;TEST PermitType ATTRIBUTE_IS_MISSING _FME_BLANK_STRING_''BOOL_OP;OR;COMPOSITE_TEST;<Unused>;TEST @LowerCase(@Value(PermitType)) CONTAINS building'Building'BOOL_OP;OR;COMPOSITE_TEST;<Unused>;TEST @LowerCase(@Value(PermitType)) CONTAINS electrical'Demolition'BOOL_OP;OR;COMPOSITE_TEST;<Unused>;TEST @LowerCase(@Value(PermitType)) CONTAINS demolition'Electrical'BOOL_OP;OR;COMPOSITE_TEST;<Unused>;TEST @LowerCase(@Value(PermitType)) CONTAINS mechanical'Mechanical'BOOL_OP;OR;COMPOSITE_TEST;<Unused>;TEST @LowerCase(@Value(PermitType)) CONTAINS plumbing'Plumbing'BOOL_OP;OR;COMPOSITE_TEST;<Unused>;TEST @LowerCase(@Value(PermitType)) CONTAINS roof'Roof'BOOL_OP;OR;COMPOSITE_TEST;<Unused>;TEST @LowerCase(@Value(PermitType)) CONTAINS fence'Fence'BOOL_OP;OR;COMPOSITE_TEST;<Unused>;TEST @LowerCase(@Value(PermitType)) CONTAINS grading'Grading'BOOL_OP;OR;COMPOSITE_TEST;<Unused>;TEST @LowerCase(@Value(PermitType)) CONTAINS pool/spa'Pool/Spa'FME_NUM_CONDITIONS11___
      SET_TO ContractorTradeMapped = FME_CONDITIONAL:DEFAULT_VALUE''BOOL_OP;OR;COMPOSITE_TEST;<Unused>;TEST ContractorTrade ATTRIBUTE_VALUE_NULL _FME_BLANK_STRING_;TEST ContractorTrade ATTRIBUTE_IS_EMPTY _FME_BLANK_STRING_;TEST ContractorTrade ATTRIBUTE_IS_MISSING _FME_BLANK_STRING_''BOOL_OP;OR;COMPOSITE_TEST;<Unused>;TEST @LowerCase(@Value(ContractorTrade)) CONTAINS general'General'BOOL_OP;OR;COMPOSITE_TEST;<Unused>;TEST @LowerCase(@Value(ContractorTrade)) CONTAINS electrical'Electrical'BOOL_OP;OR;COMPOSITE_TEST;<Unused>;TEST @LowerCase(@Value(ContractorTrade)) CONTAINS mechanical'Mechanical'BOOL_OP;OR;COMPOSITE_TEST;<Unused>;TEST @LowerCase(@Value(ContractorTrade)) CONTAINS plumbing'Plumbing'BOOL_OP;OR;COMPOSITE_TEST;<Unused>;TEST @LowerCase(@Value(ContractorTrade)) CONTAINS architecture'Architecture'BOOL_OP;OR;COMPOSITE_TEST;<Unused>;TEST @LowerCase(@Value(ContractorTrade)) CONTAINS engineering'Engineering'BOOL_OP;OR;COMPOSITE_TEST;<Unused>;TEST @LowerCase(@Value(ContractorTrade)) CONTAINS masonry'Masonry'BOOL_OP;OR;COMPOSITE_TEST;<Unused>;TEST @LowerCase(@Value(ContractorTrade)) CONTAINS sign'Sign'BOOL_OP;OR;COMPOSITE_TEST;<Unused>;TEST @LowerCase(@Value(ContractorTrade)) CONTAINS tent'Tent'FME_NUM_CONDITIONS11___
    -> DateFormatter
Note: Formats date based on Date_Format parameter and outputs as YYYY-MM-DD
DateFormatter
    DATE_ATTR = ExpiresDate,VoidDate,CompletedDate,IssuedDate,AppliedDate,COIssuedDate,HoldDate,StatusDate
    FMT = %Y"-"%m"-"%d
    SRCFMT = $(Date_Format)
    -> StringReplacer
Note: Removes $ symbol from money attributes
StringReplacer
    CASE = NO
    FIND_TEXT = $
    NO_MATCH = _FME_NO_OP_
    REGEXP = NO
    SRC_ATTRS = Fee,EstProjectCost
    -> AttributeRounder
Note: Rounds number to nearest value for Integer attributes
AttributeRounder
    PLACES = 0
    ROUND_TYPE = Nearest
    SRC_ATTRS = TotalSqFt AddedSqFt HousingUnits Fee
    -> AttributeManager
Note: Used to order the attributes into the correct order
AttributeManager
    -> FeatureWriter [Output]
    -> Dataset (writer SOCRATA_1) [off]
Note: To use the SocrataWriter enabled the incoming connector and update the writer's parameters in the Navigator pane
Dataset (writer SOCRATA_1)
    attributes: PermitNum text, Description text, AppliedDate calendar_date, IssuedDate calendar_date, CompletedDate calendar_date, StatusCurrent text, OriginalAddress1 text, OriginalAddress2 text, OriginalCity text, OriginalState text, OriginalZip text, Jurisdiction text, PermitClass text, PermitClassMapped text, StatusCurrentMapped text, WorkClass text, WorkClassMapped text, PermitType text, PermitTypeMapped text, PermitTypeDesc text, StatusDate calendar_date, TotalSqFt number, Link text, Latitude number, Longitude number, EstProjectCost number, HousingUnits number, PIN text, ContractorCompanyName text, ContractorTrade text,
      ContractorTradeMapped text, ContractorLicNum text, ContractorStateLic text, ProposedUse text, AddedSqFt number, RemovedSqFt number, MasterPermitNum text, ExpiresDate calendar_date, COIssuedDate calendar_date, HoldDate calendar_date, VoidDate calendar_date, ProjectName text, ProjectID text, TotalFinishedSqFt text, TotalUnfinishedSqFt text, TotalHeatedSqFt text, TotalUnHeatedSqFt text, TotalAccSqFt text, TotalSprinkledSqFt text, ExtraFields text, Publisher text, Fee number, ContractorFullName text, ContractorCompanyDesc text, ContractorPhone text, ContractorAddress1 text, ContractorAddress2 text, ContractorCity text, ContractorState text, ContractorZip text,
      ContractorEmail text
Note: Writes your BLDS to a csv in a folder prescribed by the Output_Folder parameter
FeatureWriter
    CSV_APPEND = No
    CSV_DESTINATION_DATASETTYPE_VALIDATION = Yes
    CSV_EXTENSION = csv
    CSV_FIELD_NAMES = yes
    CSV_QUOTE_FIELD_NAMES = no
    CSV_QUOTE_OUTPUT = if_needed
    CSV_SEPARATOR = ,
    CSV_WRITE_SCHEMA_FILE = no
    CSV_WRITE_UTF8_BOM = yes
    DATASET = $(Output_Folder)
    DATASET_ATTR = _dataset
    FEATURE_TYPE_LIST_ATTR = _feature_type
    FORMAT = CSV
    TOTAL_FEATURES_WRITTEN_ATTR = _total_features_written
    WRITER_DIRECTIVES = EXTENSION,csv,QUOTE_OUTPUT,if_needed,APPEND,No,FIELD_NAMES,yes,WRITE_SCHEMA_FILE,no,QUOTE_FIELD_NAMES,no,DESTINATION_DATASETTYPE_VALIDATION,Yes,SEPARATOR,,,WRITE_UTF8_BOM,yes

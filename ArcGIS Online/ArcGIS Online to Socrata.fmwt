FME workspace ArcGIS Online to Socrata.fmwt
Title: ArcGIS Online to Socrata
Description: This Socrata FME template is designed to provide a jump-start to easily publish data from your ArcGIS online account into Socrata.

Parameters:
- SourceDataset_ARCGISONLINEFEATURES = www.arcgis.com   # Host
- socrata_username = chris.metcalf@socrata.com   # Username
- socrata_app_token = CGxaHQoQlgQSev4zyUh5aR5J3   # App Token
- socrata_dataset_uid = e39b-rz36   # UID
- socrata_batch_size = 1000   # Batch Size
- socrata_domain = soda.demo.socrata.com   # Domain
- DestDataset_SOCRATA = your.domain.com   # Host

Readers:
- ARCGISONLINEFEATURES_1: ARCGISONLINEFEATURES from $(SourceDataset_ARCGISONLINEFEATURES)

Writers:
- SOCRATA_1: SOCRATA to $(DestDataset_SOCRATA)

Census_20Tracts (reader ARCGISONLINEFEATURES_1)
    attributes: FID esriFieldTypeInteger, OBJECTID esriFieldTypeDouble, CENSUS_TRA esriFieldTypeString(6), CENSUS_T_1 esriFieldTypeString(11), TRACT_FIPS esriFieldTypeString(5), TRACT_CENT esriFieldTypeDouble, TRACT_CE_1 esriFieldTypeDouble, TRACT_CE_2 esriFieldTypeDouble, TRACT_CE_3 esriFieldTypeDouble, TRACT_COMM esriFieldTypeString(2), TRACT_NUMA esriFieldTypeSmallInteger, TRACT_CENS esriFieldTypeSmallInteger, PERIMETER esriFieldTypeDouble, DATA_ADMIN esriFieldTypeDouble, TRACT_CREA esriFieldTypeString(10), TRACT_CR_1 esriFieldTypeDate, SHAPE_AREA esriFieldTypeDouble, SHAPE_LEN esriFieldTypeDouble, GlobalID
    -> CenterPointReplacer
CenterPointReplacer
    CENTERPOINT -> Reprojector
Reprojector
    DEST = LL-WGS84
    RASTER_CELL_SIZE = Preserve Cells
    STROKE_ARCS = Yes
    SOURCE = Read from feature
    INTERPOLATION_TYPE_NAME = Nearest Neighbor
    REPROJECTED -> New dataset (writer SOCRATA_1)
Note: Write output to Socrata. Make sure you set: / - Username / - Password / - Domain / - Dataset Name (ID)
New dataset (writer SOCRATA_1)
    attributes: FID text, OBJECTID text, CENSUS_TRA text, CENSUS_T_1 text, TRACT_FIPS text, TRACT_CENT text, TRACT_CE_1 text, TRACT_CE_2 text, TRACT_CE_3 text, TRACT_COMM text, TRACT_NUMA text, TRACT_CENS text, PERIMETER text, DATA_ADMIN text, TRACT_CREA text, TRACT_CR_1 text, SHAPE_AREA text, SHAPE_LEN text, GlobalID text

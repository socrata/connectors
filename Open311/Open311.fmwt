FME workspace Open311.fmwt
Title: Open311
Description: This Socrata FME template is designed to provide a jump-start to easily publish data into Socrata using the Open311 standard.

Parameters:
- open311_root =   # Open311 Request Endpoint
- open311_image_root =   # The root to prepend to media_urls
- socrata_username =   # Socrata Username
- socrata_password =   # Socrata Password
- socrata_app_token = CGxaHQoQlgQSev4zyUh5aR5J3   # Socrata App Token
- socrata_dataset_uid =   # Dataset UID
- socrata_domain =   # Socrata Domain
- socrata_batch_size = 1000   # Batch Size
- feed_city =   # City
- feed_state =   # State
- DestDataset_SOCRATA = your.domain.com   # Host

Writers:
- SOCRATA_1: SOCRATA to $(DestDataset_SOCRATA)

Note: Fetch data from the Open311 Feed. Make sure you set: / - open311_root / - open311_image_root (opt)
Open311_Creator: PythonCreator
    PYTHONSOURCE:
      import fmeobjects
      import json
      import urllib2
      import datetime
      import dateutil.parser
      import dateutil.tz

      # Template Class
      class FeatureCreator(object):
          def __init__(self):
              self.logger = fmeobjects.FMELogFile()

          def close(self):
              end_date = datetime.datetime.now(dateutil.tz.tzlocal())
              count = 0
              while True:
                  try:
                      # Pull a batch of requests
                      request_url = "%s?end_date=%s" % (FME_MacroValues['open311_root'], end_date.isoformat())
                      self.logger.logMessageString("Fetching %s" % request_url)
                      response = json.loads(urllib2.urlopen(urllib2.Request(request_url)).read())
                  except urllib2.HTTPError as e:
                      # TODO: Smart error handling and stuff
                      self.logger.logMessageString("Code: %s" % e.code)
                      self.logger.logMessageString("Error: %s" % e.read())
                      break

                  if len(response) <= 0:
                      self.logger.logMessageString("Done!")
                      break

                  self.logger.logMessageString("Count: %s" % count)

                  for entry in response:
                      feature = fmeobjects.FMEFeature()
                      new_end = dateutil.parser.parse(entry["requested_datetime"])

                      if new_end < end_date:
                          end_date = new_end

                      for key, value in entry.iteritems():
                          if key == "media_url" and len(value) > 0 and len(FME_MacroValues['open311_image_root']) > 0:
                              value = FME_MacroValues['open311_image_root'] + value
                          feature.setAttribute(key, value);

                      count = count + 1
                      self.pyoutput(feature)
    PYTHONSYMBOL = FeatureCreator
    NEW_ATTRIBUTES = service_request_id status lat long service_name description status_notes service_code agency_responsible service_notice requested_datetime updated_datetime expected_datetime address address_id zipcode media_url
    -> VertexCreator
Note: Add a point based on the lat/long
VertexCreator
    MODE_NAME = Add Point
    XVAL = @Value(long)
    YVAL = @Value(lat)
    -> CityStateCreator
Note: Add the city/state: / - feed_city / - feed_state
CityStateCreator: AttributeCreator
    ATTR_LIST = city,$(feed_city),state,$(feed_state)
    -> RemapToSocrata
Note: Remap Fields
RemapToSocrata: AttributeRenamer
    ATTR_LIST = service_request_id,ticket_id,"",service_name,issue_type,"",description,issue_description,"",address,street_address,"",zipcode,zip_code,"",requested_datetime,ticket_created_date_time,"",updated_datetime,ticket_last_updated_date_time,"",status,ticket_status,"",media_url,image,""
    -> New dataset (writer SOCRATA_1)
Note: Write output to Socrata. Make sure you set: / - Username / - Password / - Domain / - Dataset Name (ID)
New dataset (writer SOCRATA_1)
    attributes: ticket_id text, ticket_status text, lat text, long text, issue_type text, issue_description text, status_notes text, service_code text, agency_responsible text, service_notice text, ticket_created_date_time text, ticket_last_updated_date_time text, expected_datetime text, street_address text, address_id text, zip_code text, image text, city text, state text

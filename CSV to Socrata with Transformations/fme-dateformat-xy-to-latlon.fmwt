FME workspace fme-dateformat-xy-to-latlon.fmwt
Title: fme-dateformat-xy-to-latlon
Description: Reads data from a CSV, transform date from dd/mm/yyyy to yyyy/mm/dd, reproject X/Y to Lat/Lon and publish the result as a Socrata.

Parameters:
- SourceDataset_CSV = $(FME_MF_DIR)1/Downloads/DCCCustomerServiceRequests_P20130409-0956.csv   # Source CSV (CommaSeparatedValue) File(s)

Readers:
- CSV_1: CSV from $(SourceDataset_CSV) in EPSG:2157

Writers:
- SOCRATA_1: SOCRATA in LL-WGS84

Note: Read the CSV
CSV (reader CSV_1)
    attributes: INCIDENT_NUMBER number(7,0), SR_CREATION_CHANNEL char(6), INCIDENT_ADDRESS char(90), STATUS char(8), GROUP_NAME char(30), NAME char(31), INCIDENT_DATE char(11), ATTRIBUTE5 number(10,2), ATTRIBUTE6 number(10,2)
    -> DateFormatter
Note: Transform date from dd/mm/yyyy to yyyy/mm/dd
DateFormatter
    FMT = ISO Date (%Y-%m-%d)
    DATE_ATTR = INCIDENT_DATE
    SRCFMT = Unknown - Automatic Detection
    INVALID_DATE_VALUE = _FME_NO_OP_
    -> AttributeReprojector
Note: Reproject from Irish Transverse Mercator to WGS84 Lat/Lon
AttributeReprojector
    DEST = LL-WGS84
    YATTR = ATTRIBUTE6
    SOURCE = EPSG:2157
    XATTR = ATTRIBUTE5
    -> StringConcatenator
Note: Concatenate the lat/lon fields
StringConcatenator
    ACTION = Create New Attribute
    PARM_LINE = (@Value(ATTRIBUTE6), @Value(ATTRIBUTE5))
    VAL_ATTR = _result
    -> AttributeRenamer
Note: Rename the fields
AttributeRenamer
    ATTR_LIST = INCIDENT_NUMBER,Incident Number,,INCIDENT_DATE,Date,,SR_CREATION_CHANNEL,Creation Channel,,INCIDENT_ADDRESS,Incident Address,,STATUS,Status,,GROUP_NAME,Group Name,,NAME,Name,,ATTRIBUTE5,Longitude,,ATTRIBUTE6,Latitude,,_result,Location,
    -> Dublin City Council Service Requests (writer SOCRATA_1)
Note: Write to your_socrata_domain.com
Dublin City Council Service Requests (writer SOCRATA_1)
    attributes: Incident Number text, Creation Channel text, Incident Address text, Status text, Group Name text, Name text, Date date, Longitude text, Latitude text, Location location

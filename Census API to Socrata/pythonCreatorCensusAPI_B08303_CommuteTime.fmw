FME workspace pythonCreatorCensusAPI_B08303_CommuteTime.fmw

Parameters:
- API_KEY = API_KEY_HERE   # Enter Census API Key
- INDICATORS = B08303_001E,B08303_002E,B08303_003E,B08303_004E,B08303_005E,B08303_006E,B08303_007E,B08303_008E,B08303_009E,B08303_010E,B08303_011E,B08303_012E,B08303_013E   # Enter Indicator code(s) as comma delimited string
- URL = http://api.census.gov/data/   # URL http Enter URL for API call
- YEARS = 2012,2013,2014   # Enter Years
- CITY1 = 63000,53   # FIPS PLACE CODE, FIPS STATE CODE
- CITY2 = 05210,53   # FIPS PLACE CODE, FIPS STATE CODE
- CITY3 = 59000,41   # FIPS PLACE CODE, FIPS STATE CODE
- CITY4 = 74060,53   # FIPS PLACE CODE, FIPS STATE CODE
- CITY5 = 05350,41   # FIPS PLACE CODE, FIPS STATE CODE
- CITY6 = 23850,41   # FIPS PLACE CODE, FIPS STATE CODE
- CITY7 = 08830,16   # FIPS PLACE CODE, FIPS STATE CODE
- CITY8 = 67000,53   # FIPS PLACE CODE, FIPS STATE CODE
- ACS_YEAR = 1   # ACS 1, 3 or 5 Year Estimate

Writers:
- SOCRATA_1: SOCRATA

Note: Filterdata / The first row of data returned by Census API for any call by City contains field names, so we are filtering out those rows by excluding any row where col0 = 'NAME'
Note: 1. Rename columns so they are meaningful / 1. col0 = City / 2. col1 = Economic Indicator Total Amount / 3. col2 - 13 = Economic Indicator Response Amounts / 4. col14 -15 = FIPS codes (state, city) / 2. Create real date field and format
Note: B08303 Commute Time - Cascadia US Cities vs Seattle
Note: Perform calculations / Since there are 9 groupings, 9 attribute creators are required and then the indicators per grouping are summed and divided by the total
Note: Helpful Census Links to see which years are available for the 1, 3 and 5 surveys / Datasets available via API - http://www.census.gov/data/developers/data-sets.html / ACS 1 Year Data - http://www.census.gov/data/developers/data-sets/acs-survey-1-year-data.html / ACS 3 Year Data - http://www.census.gov/data/developers/data-sets/acs-survey-3-year-data.html / ACS 5 Year Data - http://www.census.gov/data/developers/data-sets/acs-survey-5-year-data.html
Note: Calculate average value for Benchmark Cities / Step 1. Filter out Seattle so we can average the values of the benchmark cities / Step 2. Aggregate by Year / Step 3. Set City = Benchmark Average
Note: Generate RowID / Create unique row ids for upserts by concatenating City, Indicator and Year as there will be other workflows populating same datas with other Indicators

Bookmark: Python Script to make API call
Note: Load data using PythonCreator / Step 1. Determine # of fields returned by Indicator API call by requesting it manually and verifying count / Step 2. Manually enter Attributes to Expose in PythonCreator from col0 to however many fields are returned / Step 3. Make sure all parameters are entered (User Parameters > Published Parameters - API URL, ACS 1/3/5 Year, API Key, City & State FIPs codes, Indicators) / Metro Definitions / Principal City Name FIPS State Code FIPS Place Code / Seattle 53 63000 / Bellevue 53 05210 / Vancouver 53 74060 / Portland 41 59000 / Beaverton 41 05350 / Eugene 41 23850 / Boise City 16 08830 / Spokane 53 67000
Note: Commute Time Indicators / B08303_001E Total: / -------------------------------------------- / B08303_002 Less than 5 minutes / B08303_003 5 to 9 minutes / -------------------------------------------- / B08303_004 10 to 14 minutes / B08303_005 15 to 19 minutes / B08303_006 20 to 24 minutes / B08303_007 25 to 29 minutes / -------------------------------------------- / B08303_008 30 to 34 minutes / B08303_009 35 to 39 minutes / B08303_010 40 to 44 minutes / B08303_011 45 to 59 minutes / -------------------------------------------- / B08303_012 60 to 89 minutes / B08303_013 90 or more minutes
PythonCensusApiCityReader: PythonCreator
    PYTHONSYMBOL = PythonCensusApiCityReader.PythonCensusApiCityReader
    PYTHONSOURCE:
      import fmeobjects
      # Template Class
      class FeatureCreator(object):
          def __init__(self):
              pass
          def close(self):
              feature = fmeobjects.FMEFeature()
              self.pyoutput(feature)
    NEW_ATTRIBUTES = Year col0 col1 col2 col3 col4 col5 col6 col7 col8 col9 col10 col11 col12 col13 col14 col15
    -> AttributeFilter

Bookmark: Filter header rows
AttributeFilter
    ATTR_VALUES = <EMPTY>,<MISSING>,<NULL>,<UNFILTERED>,NAME
    ATTR_NAME = col0
    <UNFILTERED> -> TableVarRenamer

Bookmark: Rename columns & Add Year as Date
TableVarRenamer: AttributeRenamer
    ATTR_LIST = col0,City,,col1,Total,,col2,B08303_002E,,col3,B08303_003E,,col4,B08303_004E,,col5,B08303_005E,,col6,B08303_006E,,col7,B08303_007E,,col8,B08303_008E,,col9,B08303_009E,,col10,B08303_010E,,col11,B08303_011E,,col12,B08303_012E,,col13,B08303_013E,,col14,FIPS_STATE,,col15,FIPS_CITY,
    -> DateCreator
DateCreator: AttributeCreator
    ATTR_LIST = Date,1/1/@Value(Year)
    -> DateFormatter
DateFormatter
    SRCFMT = Unknown - Automatic Detection
    INVALID_DATE_VALUE = _FME_NO_OP_
    FMT = ISO Date (%Y-%m-%d)
    DATE_ATTR = Date
    -> 10MinLess
    -> 10-14Min
    -> 35-44Min
    -> 60MinMore
    -> 15-19Min
    -> 20-24Min
    -> 25-29Min
    -> 30-34Min
    -> 45-59Min

Bookmark: Create Indicator values for Measurements
10MinLess: AttributeCreator
    ATTR_LIST = Indicator,Percent of workers traveling less than 10 minutes to work,IndicatorID,B08303_Less10,IndicatorValue,@Evaluate(@Evaluate(100 * (@Value(B08303_002E) + @Value(B08303_003E))/@Value(Total)))
    -> SeattleFilter
10-14Min: AttributeCreator
    ATTR_LIST = IndicatorID,B08303_004E,Indicator,Percent of workers traveling 10 to 14 minutes to work,IndicatorValue,@Evaluate(@Evaluate(100 * (@Value(B08303_004E)/@Value(Total))))
    -> SeattleFilter
15-19Min: AttributeCreator
    ATTR_LIST = IndicatorID,B08303_005E,Indicator,Percent of workers traveling 15 to 19 minutes to work,IndicatorValue,@Evaluate(@Evaluate(100 * (@Value(B08303_005E)/@Value(Total))))
    -> SeattleFilter
20-24Min: AttributeCreator
    ATTR_LIST = IndicatorID,B08303_006E,Indicator,Percent of workers traveling 20 to 24 minutes to work,IndicatorValue,@Evaluate(@Evaluate(100 * (@Value(B08303_006E)/@Value(Total))))
    -> SeattleFilter
25-29Min: AttributeCreator
    ATTR_LIST = IndicatorID,B08303_007E,Indicator,Percent of workers traveling 25 to 29 minutes to work,IndicatorValue,@Evaluate(@Evaluate(100 * (@Value(B08303_007E)/@Value(Total))))
    -> SeattleFilter
30-34Min: AttributeCreator
    ATTR_LIST = IndicatorID,B08303_008E,Indicator,Percent of workers traveling 25 to 29 minutes to work,IndicatorValue,@Evaluate(@Evaluate(100 * (@Value(B08303_008E)/@Value(Total))))
    -> SeattleFilter
35-44Min: AttributeCreator
    ATTR_LIST = Indicator,Percent of workers traveling 35 to 44 minutes to work,IndicatorID,B08303_009E + B08303_010E,IndicatorValue,@Evaluate(@Evaluate(100 * (@Value(B08303_009E) + @Value(B08303_010E))/@Value(Total)))
    -> SeattleFilter
45-59Min: AttributeCreator
    ATTR_LIST = IndicatorID,B08303_011E,Indicator,Percent of workers traveling 45 to 59 minutes to work,IndicatorValue,@Evaluate(@Evaluate(100 * (@Value(B08303_011E)/@Value(Total))))
60MinMore: AttributeCreator
    ATTR_LIST = IndicatorID,B08303_012E + B08303_013E,Indicator,Percent of workers traveling 60 or more minutes to work,IndicatorValue,@Evaluate(@Evaluate(100 * (@Value(B08303_012E) + @Value(B08303_013E))/@Value(Total)))
    -> SeattleFilter

Bookmark: Calculate Average of Benchmark Cities
SeattleFilter: AttributeFilter
    ATTR_VALUES = <EMPTY>,<MISSING>,<NULL>,<UNFILTERED>,Seattle city, Washington
    ATTR_NAME = City
    <UNFILTERED> -> CohortAggregator
    <UNFILTERED> -> AttributeKeeper
    Seattle city, Washington -> AttributeKeeper
CohortAggregator: Aggregator
    ORDERED = No
    AGGREGATE_TYPE = Homogeneous Collection (If Possible)
    GROUP_BY = Year Indicator
    MODE = Geometry - Assemble One Level
    AV = IndicatorValue
    ACCUM_ATTRS_NAME = Yes
    AGGREGATE -> CohortBenchmarkAvgCreator
CohortBenchmarkAvgCreator: AttributeCreator
    ATTR_LIST = City,Benchmark Average
    -> AttributeKeeper
AttributeKeeper
    KEEP_ATTRS = City,Date,Year,IndicatorValue,Indicator,IndicatorID
    -> Inspector
    -> CityIdYearConcatenator

Bookmark: Create Unique RowID
CityIdYearConcatenator: AttributeConcatenator
    TRIM_OPTION = Both
    DROP_EMPTY_PARTS = No
    ATTRS = City Year IndicatorID
    ORDER = ValueNumericAscending
    CASE = No
    DEST_ATTR = RowID
    SEP = _
    -> B08303_AvgCommute (writer SOCRATA_1)

Bookmark: Publish Dataset
B08303_AvgCommute (writer SOCRATA_1)
    attributes: City text, Year text, Indicator text, IndicatorValue number, Date calendar_date, RowID text, IndicatorID text

Bookmark: Use Inspector for Debugging
Inspector

FME custom transformer AttributeConcatenator
Concatenates selected attribute values in the order specified to the "Concatenating Order" parameter.
Resulting string consists of the original attribute values delimited by identical string specified to the "Separator String" parameter.
This transformer considers both Null value and Missing attribute as an empty string. 
See also the AttributeListPopulator.
Parameters
Attributes to Concatenate:
Select attributes which should be concatenated.
Concatenating Order:
Choose one of these as the concatenating order.
- Value Numeric Ascending: sorted by attribute value numeric ascending
- Value Numeric Descending: sorted by attribute value numeric descending
- Value Alphabetic Ascending: sorted by attribute value alphabetic ascending
- Value Alphabetic Descending: sorted by attribute value alphabetic descending
- Name Ascending (Alphabetic): sorted by attribute name alphabetic ascending
- Name Descending (Alphabetic): sorted by attribute name alphabetic descending
Note:
In "Value Numeric Ascending/Descending", the transformer considers every non-numeric value (including empty/null/missing) as 0.
But a numeric representation surrounded by white spaces will be treated as a numeric value (both leading and trailing white spaces will be ignored).
And leading 0 of a numeric representation will also be ignored when comparing it as a numeric value to other values.
Case Sensitive:
Yes: The transformer will perform case-sensitive sorting.
No (default): The transformer will perform case-insensitive sorting.
Note
The "Case Sensitive" parameter setting is basically applied to alphabetic sorting, but it will also be applied to non-numeric parts in numeric sorting, if non-numeric values exist.
Separator String:
Specify a string that will be used as the delimiter. You can set blank to this parameter not to use delimiter.
Trim Whitespaces:
By default, the transformer will remove Both leading and trailing whitespaces from every original attribute value before concatenating, but you can change the setting to either Left or Right, or None.
Destination Attribute:
Specify name of the attribute that stores the resulting string.
Drop Empty Parts:
Yes: The concatenation will be performed excluding empty parts.
No (default): The concatenation will be performed including empty parts.
Copyright (c) 2014 pragmatica inc. 
Permission is granted to anyone, free of charge, to use, modify and distribute the object code form of this transformer for any purpose, subject to the following restrictions: 
1) The origin of this transformer and associated FME(R) software must not be misrepresented. 
2) This transformer may only be used in conjunction with a validly licensed copy of FME software. 
THIS SOFTWARE IS PROVIDED BY PRAGMATICA INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL PRAGMATICA INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- ATTRS =   # " " Attributes to Concatenate
- ORDER = ValueNumericAscending
- CASE = No   # Case Sensitive
- SEP = ,   # Separator String
- TRIM_OPTION = Both   # Trim Whitespaces
- DEST_ATTR = _concatenated   # Destination Attribute
- DROP_EMPTY_PARTS = No   # Drop Empty Parts

Input (input)
    -> ParameterFetcher
ParameterFetcher
    ATTR_LIST = attributeconcatenator.attrs {$(ATTRS)} attributeconcatenator.sep {$(SEP)} attributeconcatenator.order {$(ORDER)} attributeconcatenator.case {$(CASE)} attributeconcatenator.trim_option {$(TRIM_OPTION)} attributeconcatenator.drop_empty {$(DROP_EMPTY_PARTS)}
    -> TclCaller
TclCaller
    SRC:
      proc concatAttrs {} {
          set attrs [FME_GetAttribute "attributeconcatenator.attrs"];
          set order [FME_GetAttribute "attributeconcatenator.order"];
          set nocase [string equal [FME_GetAttribute "attributeconcatenator.case"] {No}];
          set trimOption [FME_GetAttribute "attributeconcatenator.trim_option"];
          set trimOption [string map {Both trim Left trimleft Right trimright None ""} $trimOption];
          set keepEmpty [string equal [FME_GetAttribute "attributeconcatenator.drop_empty"] {No}];
          set sorted {};
          proc getAttr {name trimOption} {
              if {[string equal $trimOption {}]} {
                  return [FME_GetAttribute $name];
              } else {
                  return [string $trimOption [FME_GetAttribute $name]];
              };
          };
          if {[regexp {^ValueNumeric.+} $order]} {
              set num {}; set nan {};
              foreach name $attrs {
                  set v [getAttr $name $trimOption];
                  if {$keepEmpty || ![string equal $v {}]} {
                      set t [string trim $v]
                      set n [string trimleft [string range $t 0 end-1] {0}][string index $t end];
                      if {[string is double -strict $n]} {
                          lappend num [list $n $v];
                      } else {
                          lappend nan [list {0} $v];
                      };
                  };
              };
              if {$nocase} {
                  set nan [lsort -nocase -index 1 $nan];
              } else {
                  set nan [lsort -index 1 $nan];
              };
              foreach vv [lsort -real -index 0 [concat $nan $num]] {
                  lappend sorted [lindex $vv 1];
              };
          } elseif {[regexp {^ValueAlphabetic.+} $order]} {
              foreach name $attrs {
                  set v [getAttr $name $trimOption];
                  if {$keepEmpty || ![string equal $v {}]} {
                      lappend sorted $v;
                  };
              };
              if {$nocase} {
                  set sorted [lsort -nocase $sorted];
              } else {
                  set sorted [lsort $sorted];
              };
          } elseif {[regexp {^Name.+} $order]} {
              if {$nocase} {
                  set attrs [lsort -nocase $attrs];
              } else {
                  set attrs [lsort $attrs];
              };
              foreach name $attrs {
                  set v [getAttr $name $trimOption];
                  if {$keepEmpty || ![string equal $v {}]} {
                      lappend sorted $v;
                  };
              };
          } else {
              return "Debug: Invalid Concatenation Order: $order";
          };
          set delim [FME_GetAttribute "attributeconcatenator.sep"];
          if {[regexp {.+Ascending$} $order]} {
              return [join $sorted $delim];
          } elseif {[regexp {.+Descending$} $order]} {
              return [join [lreverse $sorted] $delim];
          } else {
              return "Debug: Invalid Concatenation Order: $order";
          };
      }
    TCLPROG = concatAttrs
    VAL_ATTR = attributeconcatenator.dest_attr
    -> BulkAttributeRenamer
BulkAttributeRenamer
    REPLACE_STR = $(DEST_ATTR)
    REPLACE_PATTERN = .+
    ATTRCHOICE = Selected Attributes
    ATTRLIST = attributeconcatenator.dest_attr
    PATTERN_ACTION_DISP = Regular Expression Replace
    -> BulkAttributeRemover
BulkAttributeRemover
    ATTR_EXP = ^attributeconcatenator.+
    -> Output (output)
Output (output)

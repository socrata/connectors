FME workspace SeeClickFix_Connector_2018.0.fmw
Title: SeeClickFix_API_Connector
Description: SeeClickFix API Connector
This workspace pulls all service request records and related questions/answers for a given SeeClickFix client and publishes them to two Socrata datasets.
Required User Parameters:
SeeClickFix Place URL: The entity whose SeeClickFix records will be returned.
To learn more about SeeClickFix places visit their geography documentation.
Optional User Parameters (used in the Socrata Writer):
Socrata Domain
Socrata Username (with sufficient privileges)
Socrata Password
This workspace maps some of the fields that are in the SeeClickFix (SCF) API and publishes it to a Socrata dataset. All fields are extracted from the API, but not exposed in this workspace. No authentication is required for the API so only public data is returned.
Fields in this workspace are not mapped to any other values, they are the raw values from SCF (except where dates/text must be formatted for Socrata ingress). The 'details' portion of the API response contains the question/answers that may be built into the SCF framework by the organization. Note, not all service requests will have questions to go with them.
The workspace only calls requests for a single client, there are no queries applied to the API call so all records for the client are returned. As the request count in SCF grows over time, a query should used to limit what is returned from the API.
If there are related questions structured within your SCF account, the workspace will retrieve the Q/A data with the service requests when available. They will be split into a separate data stream from the service requests to handle the difference in data schemas. Each question will become a feature and numbered to match the order of the related questions in SCF.
Additional data is derived from the data output from the API including:
Hours to acknowledge
Days since update
Days open
Day of week created, acknowledged, updated and closed
To write to a Socrata Dataset you can create new datasets through the workspace or publish to an existing one by updating the Dataset Name to the proper unique IDs. Service requests are written through the ‘Ticket_Writer’ FeatureWriter and the Questions are written through the ‘Question_Writer’ FeatureWriter. The publishing actions are both UPSERT, the column ‘ticket_id’ or ‘question_id’ must be set as the row identifier in the datasets’ metadata.
See the SeeClickFix API documentation for details:
http://dev.seeclickfix.com/

Parameters:
- SCF_Place =   # SeeClickFix Place URL
- domain = https://
- username =
- password =
- FME_SHAREDRESOURCE_DATA = /Users/chris.desisto/Downloads/   # FME Server Resource Data

Note: Workspace Name: SeeClickFix_Connector_2018.0.fmw / Author(s): Chris De Sisto - chris.desisto@tylertech.com / FME version: 2018.0.0.0 (20180308 - Build 18284 - macosx) / Key Transforms: Use HTTPCaller to pull SeeClickFix issues/requests. A loop in the custon transformer SeeClickFixAPI uses the 'next page' metadata to call all data / Key Parameters: 'SCF_Place' which enables the URL to pull from only a specified SCF organization. More details here: http://dev.seeclickfix.com/v2/places/ / Future Improvements: Paralellize the calls so run time is shorter or make a fewer number of API calls by calling only new or open service requests. Derive further data from date/time columns including time to close, time open, day of week, etc.
Creator_2
    GEOMTYPE = Geometry Object
    NUM = 1
    CREATED -> VariableSetter

Bookmark: 010. Make the API Calls and Create one Feature Per Issue/Ticket
Note: Set variable _scf_url that is first API call. Includes SCF_Place
VariableSetter
    SCOPE = Global
    VALUE = https://seeclickfix.com/api/v2/issues?place_url=$(SCF_Place)&per_page=30&details=true
    VARNAME = _scf_url
    -> SeeClickFixAPi
Note: Gets JSON response for all API calls
SeeClickFixAPi
    _CREATION_INSTANCE = @Value(_creation_instance)
    -> JSONFragmenter
Note: Makes each request a feature and exposes the attributes for the workspace
JSONFragmenter
    EXPLODE_FORMAT = JSON
    EXTRACT_ATTR = Yes
    JSON_ATTR = _issues
    JSON_QUERY = json[*]
    NEW_ATTRIBUTES = id status summary description rating lat lng address created_at acknowledged_at closed_at reopened_at updated_at comments_count html_url request_type.title questions request_type.organization media.representative_image_url
    RECURSIVE = Yes
    REJECT_EMPTY_LISTS = YES
    FRAGMENTS -> JSONExtractor
    FRAGMENTS -> AttributeManager

Bookmark: 020. Extract Questions from API Response
Note: Extract 'questions' from JSON response
JSONExtractor
    EXTRACT_QUERY_TABLE = Questions json["questions"]
    JSON_DOCUMENT = @Value(_issues)
    EVALUATED -> Tester_4
Note: Passes features with non null Questions
Tester_4
    BOOL_OP = OR
    TEST_CLAUSE = TEST @Value(Questions) != null
    PASSED -> JSONFragmenter_3
Note: Make each question a feature
JSONFragmenter_3
    EXPLODE_FORMAT = JSON
    EXTRACT_ATTR = Yes
    JSON_ATTR = Questions
    JSON_QUERY = json[*]
    NEW_ATTRIBUTES = question answer
    RECURSIVE = Yes
    REJECT_EMPTY_LISTS = NO
    FRAGMENTS -> AttributeManager_4
Note: Modify attributes for dataset
AttributeManager_4
    ATTR_TABLE:
      RENAME_SET_VALUE id > request_id
      RENAME_SET_VALUE json_index > question_number = @Evaluate(@Value(question_number)+1)
      SET_TO question_id = @Value(request_id)-@Value(question_number)
      RENAME_SET_VALUE request_type.title > issue_type
      RENAME_SET_VALUE html_url > seeclickfix_url
      REMOVE request_type.organization
      REMOVE _issues
      REMOVE json_type
      REMOVE summary
      REMOVE description
      REMOVE rating
      REMOVE lat
      REMOVE lng
      REMOVE address
      REMOVE created_at
      REMOVE acknowledged_at
      REMOVE closed_at
      REMOVE reopened_at
      REMOVE updated_at
      REMOVE comments_count
      REMOVE questions
      REMOVE media.representative_image_url
      REMOVE Questions
    -> StringReplacer_3
Note: Replace quotes next to numbers to be "inches"
StringReplacer_3
    CASE = NO
    FIND_TEXT = \d"
    NO_MATCH = _FME_NO_OP_
    REGEXP = YES
    REPLACE_TEXT = inches
    SRC_ATTRS = answer
    -> StringReplacer_4
Note: Strip remaining quotes. FME exports quote as \" and Socratadoesn't like it.
StringReplacer_4
    CASE = NO
    FIND_TEXT = "
    NO_MATCH = _FME_NO_OP_
    REGEXP = NO
    SRC_ATTRS = answer
    -> Question_Writer [SeeClickFix Questions]

Bookmark: Z001. Writes Questions to Socrata
Note: Upserts questions, uses question_id as a row identifier
Question_Writer: FeatureWriter [off]
    DATASET_ATTR = _dataset
    FEATURE_TYPE_LIST_ATTR = _feature_type
    FORMAT = SOCRATA
    SOCRATA_DOMAIN = $(domain)
    SOCRATA_PASSWORD = $(password)
    SOCRATA_SET_ASIDE_ERRORS = No
    SOCRATA_USER = $(username)
    SOCRATA_USE_API_NAMES = No
    TOTAL_FEATURES_WRITTEN_ATTR = _total_features_written

Bookmark: 030. Modify Attributes to Clean-up Schema, make description >5,000 char
Note: Rename/Remove attributes
AttributeManager
    ATTR_TABLE:
      RENAME_SET_VALUE request_type.title > issue_type
      RENAME_SET_VALUE request_type.organization > organization
      REMOVE questions
      RENAME_SET_VALUE media.representative_image_url > image_url
      REMOVE _issues
      REMOVE json_type
      REMOVE json_index
    -> DateTimeConverter_2
Note: Convert all time fields to FME time. Required for Date Time calculations in Derived Data
DateTimeConverter_2
    DATETIME_ATTR = closed_at updated_at created_at acknowledged_at reopened_at
    IN_FORMAT = %Y-%m-%dT%H:%M:%S%Ez$
    OUT_FORMAT = FME
    REPAIR_INPUT = NO
    -> AttributeManager_8
    <REJECTED> -> AttributeManager_8
Note: Removes time zone from all time attributes
AttributeManager_8
    ATTR_TABLE:
      SET_TO created_at = FME_CONDITIONAL:DEFAULT_VALUE'_FME_NO_OP_'BOOL_OP;OR;COMPOSITE_TEST;<Unused>;TEST created_at ATTRIBUTE_HAS_A_VALUE _FME_BLANK_STRING_'@TimeZoneRemove(@Value(created_at))'FME_NUM_CONDITIONS2___
      SET_TO acknowledged_at = FME_CONDITIONAL:DEFAULT_VALUE'_FME_NO_OP_'BOOL_OP;OR;COMPOSITE_TEST;<Unused>;TEST acknowledged_at ATTRIBUTE_HAS_A_VALUE _FME_BLANK_STRING_'@TimeZoneRemove(@Value(acknowledged_at))'FME_NUM_CONDITIONS2___
      SET_TO closed_at = FME_CONDITIONAL:DEFAULT_VALUE'_FME_NO_OP_'BOOL_OP;OR;COMPOSITE_TEST;<Unused>;TEST updated_at ATTRIBUTE_HAS_A_VALUE _FME_BLANK_STRING_'@TimeZoneRemove(@Value(updated_at))'FME_NUM_CONDITIONS2___
      SET_TO reopened_at = FME_CONDITIONAL:DEFAULT_VALUE'_FME_NO_OP_'BOOL_OP;OR;COMPOSITE_TEST;<Unused>;TEST reopened_at ATTRIBUTE_HAS_A_VALUE _FME_BLANK_STRING_'@TimeZoneRemove(@Value(reopened_at))'FME_NUM_CONDITIONS2___
      SET_TO updated_at = FME_CONDITIONAL:DEFAULT_VALUE'_FME_NO_OP_'BOOL_OP;OR;COMPOSITE_TEST;<Unused>;TEST updated_at ATTRIBUTE_HAS_A_VALUE _FME_BLANK_STRING_'@TimeZoneRemove(@Value(updated_at))'FME_NUM_CONDITIONS2___
      REMOVE fme_rejection_code
    -> SubstringExtractor
Note: Trim description to 5,000 char to fit in Socrata
SubstringExtractor
    END = 5000
    RESULT_ATTR = description
    SRC_STRING = @Value(description)
    START = 0
    -> Tester_3
Note: Pass if description is 5,000 char length
Tester_3
    BOOL_OP = OR
    TEST_CLAUSE = TEST @StringLength(@Value(description)) = 5000
    PASSED -> AttributeCreator_2
    FAILED -> StringReplacer
Note: Append "..." to description
AttributeCreator_2
    ATTR_TABLE = SET_TO description = @Value(description)...
    -> StringReplacer
Note: Replace quotes next to numbers to be "inches". This is appropriate for most instances of 311 data
StringReplacer
    CASE = NO
    FIND_TEXT = \d"
    NO_MATCH = _FME_NO_OP_
    REGEXP = YES
    REPLACE_TEXT = inches
    SRC_ATTRS = description
    -> StringReplacer_2
Note: Strip remaining quotes. FME exports quote as \" and Socrata doesn't like it.
StringReplacer_2
    CASE = NO
    FIND_TEXT = "
    NO_MATCH = _FME_NO_OP_
    REGEXP = NO
    SRC_ATTRS = description,summary
    -> AttributeManager_5

Bookmark: 040. Derive Data
Note: Calculate Location, Response & Completion times in Hr & Days. Create fields for derived Day calculations in DateTimeConverters.
Note: Only calculates values if underlying values are present. Rounds to nearest day.
AttributeManager_5
    ATTR_TABLE:
      SET_TO hours_to_acknowledge = FME_CONDITIONAL:DEFAULT_VALUE'_FME_NO_OP_'BOOL_OP;AND;COMPOSITE_TEST;<Unused>;TEST acknowledged_at ATTRIBUTE_HAS_A_VALUE _FME_BLANK_STRING_;TEST created_at ATTRIBUTE_HAS_A_VALUE _FME_BLANK_STRING_'@round(@DateTimeDiff(@Value(acknowledged_at),@Value(created_at),hours),1)'FME_NUM_CONDITIONS2___
      SET_TO days_since_update = FME_CONDITIONAL:DEFAULT_VALUE'_FME_NO_OP_'BOOL_OP;AND;COMPOSITE_TEST;<Unused>;TEST @Value(status) = Open;TEST updated_at ATTRIBUTE_HAS_A_VALUE _FME_BLANK_STRING_'@round(@DateTimeDiff(@DateTimeNow(),@Value(updated_at),days),1)'FME_NUM_CONDITIONS2___
      SET_TO days_open = FME_CONDITIONAL:DEFAULT_VALUE'_FME_NO_OP_'BOOL_OP;OR;COMPOSITE_TEST;<Unused>;TEST @Value(status) = Open;TEST @Value(status) = Acknowledged'@round(@DateTimeDiff(@DateTimeNow(),@Value(created_at),days),1)'BOOL_OP;OR;COMPOSITE_TEST;<Unused>;TEST @Value(status) = Closed'@round(@DateTimeDiff(@Value(closed_at),@Value(created_at),days),1)'FME_NUM_CONDITIONS3___
      SET_TO day_created = @Value(created_at)
      SET_TO day_acknowledged = @Value(acknowledged_at)
      SET_TO day_updated = @Value(updated_at)
      SET_TO day_closed = @Value(closed_at)
      SET_TO location = (@Value(lat), @Value(lng))
    -> DateTimeConverter
Note: Extracts day of week from relevant date columns
DateTimeConverter
    DATETIME_ATTR = day_updated day_created day_acknowledged day_closed
    IN_FORMAT = FME
    OUT_FORMAT = %a
    REPAIR_INPUT = NO
    -> TicketWriter [Output]
    <REJECTED> -> TicketWriter [Output]

Bookmark: Z001. Writes Tickets to Socrata
Note: Upserts tickets, uses ticket_id as a row identifier.
Note: ATTRIBUTE NAMES ARE THE API ENDPOINT NAMES. THEY CAN BE CHANGED IN THE WRITER USING PARAMETERS > ADVANCED > ATTRIBUTE NAMES ARE API ENDPOINTS
TicketWriter: FeatureWriter [off]
    DATASET_ATTR = _dataset
    FEATURE_TYPE_LIST_ATTR = _feature_type
    FORMAT = SOCRATA
    SOCRATA_DOMAIN = $(domain)
    SOCRATA_PASSWORD = $(password)
    SOCRATA_SET_ASIDE_ERRORS = No
    SOCRATA_USER = $(username)
    SOCRATA_USE_API_NAMES = Yes
    TOTAL_FEATURES_WRITTEN_ATTR = _total_features_written

FME custom transformer SeeClickFixAPi

Parameters:
- _CREATION_INSTANCE = @Value(_creation_instance)   # Creation Instance

Input (input)
    -> AttributeManager_2
Note: Removes attribute that must be used to trigger CustomTransformer
AttributeManager_2
    ATTR_TABLE = REMOVE _creation_instance
    -> VariableRetriever-URL
Note: Retrieves URL variable set either in the main workspace or downstream in the custom transformer
VariableRetriever-URL
    SCOPE = Global
    VALUE_ATTR = _scf_url
    VARNAME = _scf_url
    -> HTTPCaller
Note: GETS _scf_url which is set as the variable by the VariableSetter on the main canvas or by the VariableSetter in this custrom tansformer and looped. / details=true -- returns the secondary questions / per_page=30 -- is the max issues returned when details=true
HTTPCaller
    CONNECTION_TIMEOUT_LENGTH = 120
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(_scf_url)
    TRANSFER_TIMEOUT_LENGTH = 90
    USE_COOKIES = No
    VERIFY_SSL_CERTIFICATES = Yes
    -> JSONExtractor
    <Rejected> -> AttributeManager
Note: Extracts _next_page_url / and issues
JSONExtractor
    EXTRACT_QUERY_TABLE = _next_page_url json["metadata"]["pagination"]["next_page_url"] _issues json["issues"]
    JSON_DOCUMENT = @Value(_response_body)
    EVALUATED -> Tester
    EVALUATED -> Output (output)
Note: Passes _next_page_url to the loop if it's present
Tester
    BOOL_OP = OR
    TEST_CLAUSE = TEST _next_page_url ATTRIBUTE_HAS_A_VALUE ""
    PASSED -> VariableSetter
Note: Sets variable as _next_page_url to be passed through HTTPCaller via loop
VariableSetter
    SCOPE = Global
    VALUE = @Value(_next_page_url)
    VARNAME = _scf_url
    -> Sampler
    -> Input (output)
Note: Enable to allow for testing of subset of API response (150 records). Also disable connection between VariableSetter and Loop to Input
Sampler [off]
    RATE = 4
    SAMPLE_MODE = No
    SAMPLE_TYPE_LONG = First N Features
    SAMPLED -> Input (output)
Note: Loop back to Input in this Custom Transformer
Input (output)
Note: Output to Main canvas
Output (output)
Note: Sets attributes for logging bad HTTP calls
AttributeManager
    ATTR_TABLE:
      RENAME_SET_VALUE _scf_url > SCF_URL
      RENAME_SET_VALUE _error > Error
      RENAME_SET_VALUE _response_body > Response_Body
      RENAME_SET_VALUE _http_status_code > HTTP_Status_Code
    -> LogFeatureWriter [Logged]
Note: Creates CSV of features that go to logger. Set file name and destination
LogFeatureWriter: FeatureWriter
    CSV2_COORDINATE_SYSTEM_GRANULARITY = FEATURE_TYPE
    CSV2_DELIMITER = ,
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_WRITE_BOM_FOR_UNICODE = Yes
    CSV2_WRITE_FIELD_NAMES = firstrow
    CSV2_WRITE_SCHEMA_FILE = NO
    DATASET = $(FME_MF_DIR_USERTYPED)\logs
    DATASET_ATTR = _dataset
    FEATURE_TYPE_LIST_ATTR = _feature_type
    FORMAT = CSV2
    TOTAL_FEATURES_WRITTEN_ATTR = _total_features_written

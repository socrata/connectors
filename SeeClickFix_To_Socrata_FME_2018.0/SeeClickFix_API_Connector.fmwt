FME workspace SeeClickFix_API_Connector.fmwt
Title: SeeClickFix_API_Connector
Description: PublicStuff API Connector:
This workspace pulls all service request records for a PublicStuff client and publishes it to a Socrata dataset.
Required User Parameters:
PublicStuff Client ID: Available to PublicStuff customers
PublicStuff API Token: Can be requested in API documentation
Optional User Parameters (used in the Socrata Writer):
Socrata Domain
Socrata Username (with sufficient privileges)
Socrata Password
This workspace maps some of the fields that are in the PublicStuff API and publishes it to a Socrata dataset. All fields are extracted through the API, but not exposed in this workspace.
Fields in this workspace are not mapped to any other values, they are the raw values from PublicStuff (except where dates/text must be formatted for Socrata ingress).
The workspace pulls records for a single PublicStuff client, there are no queries applied to the API call so all records for the client are returned. As the request count in PublicStuff grows over time, a query should used to limit what is returned from the API. The API does not return all of the fields that are available in exports from PublicStuff.
Additional data is derived from the data output from the API including:
Time to Respond
Time to Complete
Time Since Update
Day of week Created, Closed and responded 
To write to a Socrata dataset through the FeatureWriter, you can create a new dataset via the workspace or publish to an existing one by updating the Dataset Name to the proper unique ID. The publishing action is an UPSERT, the column ‘Service Request Key’ must be set as the row identifier in the dataset’s metadata.
See PublicStuff API documentation for details:
https://api.publicstuff.com/api/index.html?url=/api/api-docs.json

Parameters:
- API_TOKEN =   # API Token for Public Stuff
- Client_ID =   # PublicStuff client id

Note: Author(s): Chris De Sisto & Alicia Brown / Company: Tyler Technologies / E-mail: chris.desisto@tylertech.com / alicia.brown@tylertech.com / DevVersion: 2018.0.0.0 (20180308 - Build 18284 - macosx) / Workspace to call PublicStuff API and populate Socrata dataset / Required User Parameters: / API_TOKEN: Obtained via https://api.publicstuff.com/api/index.html?url=/api/api-docs.json / Client_ID: Obtained from SeeClickFix as a customer

Bookmark: 00. Sets API variables & makes API calls
  Variables are used on custom transformer
Creator
    GEOMTYPE = Geometry Object
    NUM = 1
    CREATED -> VariableSetter-URL
Note: Sets api_url as variable to be used throughout workspace
VariableSetter-URL
    SCOPE = Global
    VALUE = https://api.publicstuff.com/app/requests?client_id=$(Client_ID)&limit=500
    VARNAME = api_url
    -> VariableSetter-Token
Note: Sets API Token as variable to be used throughout workspace. SET THIS VALUE USING THE PARAMETER $(API_TOKEN)
VariableSetter-Token
    SCOPE = Global
    VALUE = $(API_TOKEN)
    VARNAME = token
    -> Public_Stuff_API
Note: Custom transformer. See 'Public Stuff API' tab
Public_Stuff_API: Public Stuff API
    Reject -> AttributeManager_2
    -> JSONFragmenter
AttributeManager_2
    ATTR_TABLE:
      REMOVE _creation_instance
      RENAME_SET_VALUE _url > URL
      RENAME_SET_VALUE _error > Error
      RENAME_SET_VALUE _response_body > Response Body
      RENAME_SET_VALUE _http_status_code > HTTP Status Code
      SET_TO Date Time = @DateTimeNow()
    -> LogFeatureWriter [Logged]
Note: Creates CSV of features that go to logger.
LogFeatureWriter: FeatureWriter
    CSV2_COORDINATE_SYSTEM_GRANULARITY = FEATURE_TYPE
    CSV2_DELIMITER = ,
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_WRITE_BOM_FOR_UNICODE = Yes
    CSV2_WRITE_FIELD_NAMES = firstrow
    CSV2_WRITE_SCHEMA_FILE = NO
    DATASET = $(FME_MF_DIR_USERTYPED)\logs
    DATASET_ATTR = _dataset
    FEATURE_TYPE_LIST_ATTR = _feature_type
    FORMAT = CSV2
    TOTAL_FEATURES_WRITTEN_ATTR = _total_features_written

Bookmark: 10. Exposes PublicStuff attributes from JSON response
Note: Expose Attributes from JSON response
JSONFragmenter
    EXPLODE_FORMAT = JSON
    EXTRACT_ATTR = Yes
    JSON_ATTR = entities
    JSON_QUERY = json[*]
    NEW_ATTRIBUTES = properties.id properties.request_type_name properties.geo_location.name properties.description properties.priority properties.status properties.created_at properties.updated_at properties.completed_at properties.api_source_name properties.geo_location.latitude properties.geo_location.longitude properties.geo_location.postal_address.name properties.geo_location.postal_address.formatted_address properties.geo_location.postal_address.street_number properties.geo_location.postal_address.street_name properties.geo_location.postal_address.street_type properties.geo_location.postal_address.street_direction properties.geo_location.postal_address.postal_code properties.responded_at properties.response_time_s properties.completion_time_s properties.request_type_name
    RECURSIVE = Yes
    FRAGMENTS -> AttributeManager
    <REJECTED> -> AttributeManager_3
Note: Renames PublicStuff attributes from API names to 311 Service Request names
AttributeManager
    ATTR_TABLE:
      RENAME_SET_VALUE properties.id > Service Request Key
      RENAME_SET_VALUE properties.request_type_name > Request Type Name
      RENAME_SET_VALUE properties.description > Description
      RENAME_SET_VALUE properties.priority > Request Type Code
      RENAME_SET_VALUE properties.status > Status Code
      RENAME_SET_VALUE properties.created_at > Created Date Time
      RENAME_SET_VALUE properties.responded_at > Responded Date Time
      RENAME_SET_VALUE properties.updated_at > Updated Date Time
      RENAME_SET_VALUE properties.completed_at > Completed Date Time
      RENAME_SET_VALUE properties.api_source_name > Intake Form
      RENAME_SET_VALUE properties.geo_location.latitude > Latitude
      RENAME_SET_VALUE properties.geo_location.longitude > Longitude
      RENAME_SET_VALUE properties.geo_location.name > Address
      RENAME_SET_VALUE properties.response_time_s > Time Response Total Sec
      RENAME_SET_VALUE properties.completion_time_s > Time Completion Total Sec
      RENAME_SET_VALUE properties.geo_location.postal_address.name > Postal Address
      RENAME_SET_VALUE properties.geo_location.postal_address.formatted_address > Address
      RENAME_SET_VALUE properties.geo_location.postal_address.street_number > Street Number
      RENAME_SET_VALUE properties.geo_location.postal_address.street_name > Street Name
      RENAME_SET_VALUE properties.geo_location.postal_address.street_type > Street Type
      RENAME_SET_VALUE properties.geo_location.postal_address.street_direction > Street Direction
      RENAME_SET_VALUE properties.geo_location.postal_address.postal_code > ZIP Code
      REMOVE _creation_instance
      REMOVE entities
      REMOVE json_type
      REMOVE json_index
      REMOVE _url
      REMOVE _response_body
      REMOVE _http_status_code
    -> DuplicateFilter
Note: Only passes unique Service Request Key
DuplicateFilter
    INPUT_ORDERED_CHOICE = No
    KEYATTR = Service Request Key
    UNIQUE -> DateTimeConverter_3
    DUPLICATE -> AttributeManager_4
Note: Converts all times to FME time to allow calculations. Rejected attributes are ones without values
DateTimeConverter_3
    DATETIME_ATTR = Completed Date Time Responded Date Time Updated Date Time Created Date Time
    IN_FORMAT = %Y-%m-%dT%H:%M:%SZ
    OUT_FORMAT = FME
    REPAIR_INPUT = NO
    -> AttributeManager_5
    <REJECTED> -> AttributeManager_5

Bookmark: 20. Derive Data
Note: Calculate Response & Completion times in Hr & Days. Create fields for derived Day calculations in DateTimeConverters
Note: Calculations run if source time value (seconds) is >0. Otherwise memory overloads while running.
AttributeManager_5
    ATTR_TABLE:
      SET_TO Time Response Total Days = FME_CONDITIONAL:DEFAULT_VALUE'_FME_NO_OP_'BOOL_OP;OR;COMPOSITE_TEST;<Unused>;TEST @Value(Time Response Total Sec) > 0'@Evaluate(@Evaluate(@round(@Value(Time Response Total Sec)/86400),1))'FME_NUM_CONDITIONS2___
      SET_TO Time Response Total Hours = FME_CONDITIONAL:DEFAULT_VALUE'_FME_NO_OP_'BOOL_OP;OR;COMPOSITE_TEST;<Unused>;TEST @Value(Time Response Total Sec) > 0'@Evaluate(@Evaluate(@round(@Value(Time Response Total Sec)/3600),1))'FME_NUM_CONDITIONS2___
      SET_TO Time Completion Total Days = FME_CONDITIONAL:DEFAULT_VALUE'_FME_NO_OP_'BOOL_OP;OR;COMPOSITE_TEST;<Unused>;TEST @Value(Time Completion Total Sec) > 0'@Evaluate(@Evaluate(@round(@Value(Time Completion Total Sec)/86400),1))'FME_NUM_CONDITIONS2___
      SET_TO Time Completion Hours = FME_CONDITIONAL:DEFAULT_VALUE'_FME_NO_OP_'BOOL_OP;OR;COMPOSITE_TEST;<Unused>;TEST @Value(Time Completion Total Sec) > 0'@Evaluate(@Evaluate(@round(@Value(Time Completion Total Sec)/3600),1))'FME_NUM_CONDITIONS2___
      SET_TO Day Created = @Value(Created Date Time)
      SET_TO Day Completed = @Value(Completed Date Time)
      SET_TO Day Responded = @Value(Responded Date Time)
      SET_TO Update Days Since = @Value(Updated Date Time)
    -> DateTimeConverter
Note: Extracts day of week from relevant date columns
DateTimeConverter
    DATETIME_ATTR = Day Completed Day Responded Day Created
    IN_FORMAT = FME
    OUT_FORMAT = %a
    REPAIR_INPUT = NO
    -> Tester
    <REJECTED> -> Tester
Note: Passes non COMPLETE requests for analysis
Tester
    BOOL_OP = OR
    TEST_CLAUSE = TEST @Value(Status Code) != COMPLETED
    PASSED -> DateTimeCalculator
    FAILED -> AttributeManager_7
Note: Calculate Update Days Since
DateTimeCalculator
    MODE = DATETIMECALC_3_CALCULATE_INTERVAL
    OPERATION_PARAMETERS = START_DATETIME]@Value(Update Days Since)]END_DATETIME]@DateTimeNow()]RESULT_TYPE]DAYS]RESULT_INTERVAL]Update Days Since]FME_CONTROLLER_QUERY_FILE]transformers/dependencies/datetimecalculator/DATETIMECALC_3_CALCULATE_INTERVAL.fme
    -> AttributeManager_6
Note: Delete Update Days Since to make COMPLETE requests null
AttributeManager_7
    ATTR_TABLE = REMOVE Update Days Since
    -> AttributeManager_6
Note: Round Update Days Since and remove FME attributes
AttributeManager_6
    ATTR_TABLE:
      SET_TO Update Days Since = @Evaluate(@round(@Value(Updated Date Time)))
      REMOVE fme_rejection_code
      REMOVE Update Days Since
    -> AttributeManager_8

Bookmark: 30. Preps for Socrata Ingress
Note: **Truncates Description to 5,000 char for ingress** - Cannot rename and set attribute value in AttributeManager. Create Location column
AttributeManager_8
    ATTR_TABLE:
      SET_TO Description = @Left(@Value(Description),5000)
      SET_TO Location = FME_CONDITIONAL:DEFAULT_VALUE'_FME_NO_OP_'BOOL_OP;OR;COMPOSITE_TEST;<Unused>;TEST Latitude ATTRIBUTE_HAS_A_VALUE _FME_BLANK_STRING_'(@Value(Latitude), @Value(Longitude))'FME_NUM_CONDITIONS2___
    -> Tester_2
Note: Replace Quotes and Carriage Returns with a space for Socrata ingress
StringReplacer-lines
    CASE = NO
    FIND_TEXT = \"|\n
    NO_MATCH = _FME_NO_OP_
    REGEXP = YES
    REPLACE_TEXT = " "
    SRC_ATTRS = Description
    -> DateFormatter
Note: Socrata Friendly Date conversion
DateFormatter
    DATE_ATTR = "Completed Date Time","Responded Date Time","Updated Date Time","Update Days Since","Created Date Time"
    FMT = ISO DateTime (%Y-%m-%dT%H:%M:%S)
    INVALID_DATE_VALUE = _FME_NO_OP_
    SRCFMT = FME
    -> FeatureWriter [CSV]

Bookmark: 30a. Adds "..." to truncated Description
Tester_2
    BOOL_OP = OR
    TEST_CLAUSE = TEST @StringLength(@Value(Description)) = 5000
    PASSED -> AttributeCreator_2
    FAILED -> StringReplacer-lines
AttributeCreator_2
    ATTR_TABLE = SET_TO Description = @Value(Description)...
    -> StringReplacer-lines

Bookmark: ZZ1. Writes to '311 Service Requests' dataset
  Requires Socrata credentials
Note: Update transformer parameters with user credentials
FeatureWriter [off]
    DATASET_ATTR = _dataset
    FEATURE_TYPE_LIST_ATTR = _feature_type
    FORMAT = SOCRATA
    SOCRATA_DOMAIN = socrata.com
    SOCRATA_PASSWORD =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
    SOCRATA_SET_ASIDE_ERRORS = No
    SOCRATA_USER = @socrata.com
    SOCRATA_USE_API_NAMES = No
    TOTAL_FEATURES_WRITTEN_ATTR = _total_features_written

Bookmark: ZZ4. Logs unfragmented dupe requests
AttributeManager_4
    ATTR_TABLE = SET_TO Date Time = @DateTimeNow()
    -> LogFeatureWriter_3 [Logged]
Note: Creates CSV of errors duplicate service requests
LogFeatureWriter_3: FeatureWriter
    CSV2_COORDINATE_SYSTEM_GRANULARITY = FEATURE_TYPE
    CSV2_DELIMITER = ,
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_WRITE_BOM_FOR_UNICODE = Yes
    CSV2_WRITE_FIELD_NAMES = firstrow
    CSV2_WRITE_SCHEMA_FILE = NO
    DATASET = $(FME_MF_DIR_USERTYPED)\logs
    DATASET_ATTR = _dataset
    FEATURE_TYPE_LIST_ATTR = _feature_type
    FORMAT = CSV2
    TOTAL_FEATURES_WRITTEN_ATTR = _total_features_written

Bookmark: ZZ3. Logs unfragmented API responses
AttributeManager_3
    ATTR_TABLE:
      RENAME_SET_VALUE _url > URL
      RENAME_SET_VALUE _response_body > Response Body
      RENAME_SET_VALUE _http_status_code > HTTP Status Code
      REMOVE _creation_instance
      SET_TO Date Time = @DateTimeNow()
    -> LogFeatureWriter_2 [Logged]
Note: Creates CSV of errors rejected features
LogFeatureWriter_2: FeatureWriter
    CSV2_COORDINATE_SYSTEM_GRANULARITY = FEATURE_TYPE
    CSV2_DELIMITER = ,
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_WRITE_BOM_FOR_UNICODE = Yes
    CSV2_WRITE_FIELD_NAMES = firstrow
    CSV2_WRITE_SCHEMA_FILE = NO
    DATASET = $(FME_MF_DIR_USERTYPED)\logs
    DATASET_ATTR = _dataset
    FEATURE_TYPE_LIST_ATTR = _feature_type
    FORMAT = CSV2
    TOTAL_FEATURES_WRITTEN_ATTR = _total_features_written

FME custom transformer Public Stuff API

Input (input)
    -> VariableRetriever-URL
AttributeRemover
    LIST_ATTRS = _headers{} _headers{}.name _headers{}.value
    -> Output (output)
Note: Sends entities to Main canvas for processing
Output (output)

Bookmark: 00. Makes API Call to https://api.publicstuff.com
Note: Retrieves URL variable set either in the main workspace or downstream in the custom transformer
VariableRetriever-URL
    SCOPE = Global
    VALUE_ATTR = _url
    VARNAME = api_url
    -> VariableRetriever-Token
Note: Retrieves token variable set in Main workspace
VariableRetriever-Token
    SCOPE = Global
    VALUE_ATTR = _token
    VARNAME = token
    -> HTTPCaller
Note: Calls URL set by VariableRetriever-URL
HTTPCaller
    CONNECTION_TIMEOUT_LENGTH = 60
    CUSTOM_HEADERS = Authorization;Token token=@Value(_token)
    ERROR_ATTR = _error
    FOLLOW_REDIRECTS = Yes
    HTTP_METHOD = GET
    RESPONSE_HEADER_LIST_ATTR = _headers
    SAVE_FILE = Attribute
    STATUS_CODE_ATTR = _http_status_code
    TARGET_ATTR = _response_body
    TARGET_ATTR_ENCODING = auto-detect
    TARGET_URL = @Value(_url)
    TRANSFER_TIMEOUT_LENGTH = 90
    USE_COOKIES = No
    VERIFY_SSL_CERTIFICATES = Yes
    -> JSONExtractor
    <Rejected> -> Reject (output)
Reject (output)

Bookmark: 01. Pagination for API to recursively hit the API based on the API response
Note: Extracts 'entities' and 'next page' details from API response
JSONExtractor
    EXTRACT_QUERY_TABLE = next_page json["properties"]["next_page"] entities json["entities"]
    JSON_DOCUMENT = @Value(_response_body)
    EVALUATED -> Tester
    <REJECTED> -> AttributeManager_3
Note: Pass = 'next page' as empty/missing/null
Tester
    BOOL_OP = AND
    TEST_CLAUSE:
      TEST next_page NOT_ATTRIBUTE_VALUE_NULL ""
      TEST next_page NOT_ATTRIBUTE_IS_EMPTY ""
      TEST next_page NOT_ATTRIBUTE_VALUE_NULL ""
    PASSED -> VariableSetter-NextPage
    FAILED -> AttributeRemover
Note: Resets URL variable based on header info to rebuild URL for next page
VariableSetter-NextPage
    SCOPE = Global
    VALUE = @Value(_url)&page=@Value(next_page)
    VARNAME = api_url
    -> Input (output) [off]
    -> AttributeRemover
Note: Loops to Input on this canvas with URL of next page to call
Input (output)

Bookmark: ZZ. Logs unfragmented API responses
Note: Retains relevant attributes for logging
AttributeManager_3
    ATTR_TABLE:
      RENAME_SET_VALUE _url > URL
      RENAME_SET_VALUE _response_body > Response Body
      RENAME_SET_VALUE _http_status_code > HTTP Status Code
      SET_TO Date Time = @DateTimeNow()
    -> LogFeatureWriter [Logged]
Note: Creates CSV of rejected features.
LogFeatureWriter: FeatureWriter
    CSV2_COORDINATE_SYSTEM_GRANULARITY = FEATURE_TYPE
    CSV2_DELIMITER = ,
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_WRITE_BOM_FOR_UNICODE = Yes
    CSV2_WRITE_FIELD_NAMES = firstrow
    CSV2_WRITE_SCHEMA_FILE = NO
    DATASET = $(FME_MF_DIR_USERTYPED)\logs
    DATASET_ATTR = _dataset
    FEATURE_TYPE_LIST_ATTR = _feature_type
    FORMAT = CSV2
    TOTAL_FEATURES_WRITTEN_ATTR = _total_features_written

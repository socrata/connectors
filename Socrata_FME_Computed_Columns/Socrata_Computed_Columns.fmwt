FME workspace Socrata_Computed_Columns.fmwt
Title: Socrata_Computed_Columns
Description: Writing to a Socrata Dataset with Computed Columns
When using the Socrata Writer to update an existing dataset that has computed columns, you may encounter a failure message that looks like this:
Polling the job status: FAILURE: Processing TEMP.csv.sdiff.gz failed: Fields not in dataset: ":@computed_region_4b54_tmc4", ":@computed_region_p8tp_5dkv", ":@computed_region_4a3i_ccfj", ":@computed_region_kxmf_bzkv"
Datasets that have location data that intersects a Spatial Lens Boundary will have computed columns. These columns are created and curated by the Socrata platform, not the user. They are used to perform the geographic join between the geocoded row and the underlying spatial lens polygon. The column names begin with the prefix :@computed_region_
These rows are hidden from default views of the dataset, so the Socrata user rarely interacts with them. However, when the Socrata Writer tries to write to a dataset with computed columns it tries to find them within the Socrata Writer’s payload, and they are not there. 
As a workaround, this FME workspace will use a headless DataSync job to update the existing dataset rather than the Socrata Writer. You will need to have DataSync installed for this process. It can either be downloaded and installed, or you can use FME to find the version of DataSync you have installed within FME. To do so, run a different workspace with the Socrata Writer, and within the log, you will find the path to the .jar file. It will look something like java -jar {path to datasync}/datasync.jar This path can be used in the DataSync_Path published parameter.
Note: You will need to acquire the API field names for the columns in your dataset - you can access them by expanding the column descriptions on the dataset’s Primer Page.

Parameters:
- DataSync_Path =   # Select DataSync .jar
- Domain =   # Socrata Domain
- Username = @socrata.com   # Socrata Username
- Password =   # Socrata Password
- appToken =
- Dataset_ID =   # Dataset Unique ID
- Publish_Method = replace   # DataSync Publish Method

Note: Replace this with the incoming data that would notmally connect to the Socrata Writer
Note: This workspace is used to replace the Socrata Writer when updating an existing Socrata dataset with computed columns. / It will use a headless DataSync job to load the data to the dataset. You must have DataSync installed for this to function. It can either be downloaded and installed, or you can find the version of DataSync installed with FME. To find that, run a different workspace with the Socrata Writer and within the log, you will find the path to the .jar file, it will look something like java -jar {path to datasync}/datasync.jar This path can be used in the DataSync_Path published parameter. / Parameters: / DataSync_Path: path to the .jar file / Domain: Socrata domain to publish to / Username: Credentialed username with privelages / Password: Password for username / appToken: App token used in DataSync (not required if using DataSnc v1.9.1) / Dataset_ID: Dataset 4x4 to update - must be the UID, not the dataset name. / Publish_Method: choose the appropriate method
Tabular_Data_Payload: Creator
    GEOMTYPE = Geometry Object
    NUM = 1
    CREATED -> AttributeManager
Note: Rename ALL attributes to match api_endpoint names
AttributeManager
    ATTR_TABLE = REMOVE _creation_instance
    -> FeatureWriter [Passed]
Note: Write payload to csv - Attribute Definition = Automatic
FeatureWriter
    CSV2_COORDINATE_SYSTEM_GRANULARITY = FEATURE_TYPE
    CSV2_DELIMITER = ,
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_WRITE_BOM_FOR_UNICODE = Yes
    CSV2_WRITE_FIELD_NAMES = firstrow
    CSV2_WRITE_SCHEMA_FILE = NO
    DATASET = $(FME_MF_DIR_USERTYPED)
    DATASET_ATTR = _dataset
    FEATURE_TYPE_LIST_ATTR = _feature_type
    FORMAT = CSV2
    TOTAL_FEATURES_WRITTEN_ATTR = _total_features_written
    SUMMARY -> AttributeCreator_2
    SUMMARY -> AttributeCreator_5
Note: Creates control.json required to run DataSync. Manage synthetic columns, date formats, etc, here.
AttributeCreator_5
    ATTR_TABLE:
      SET_TO text_line_data = {
          "action" : "$(Publish_Method)",
          "csv" :
            {
              "useSocrataGeocoding" : true,
              "columns" : null,
              "skip" : 0,
              "fixedTimestampFormat" : ["yyyy/MM/dd","ISO8601","MM/dd/yy","MM/dd/yyyy"],
              "floatingTimestampFormat" : ["yyyy/MM/dd","ISO8601","MM/dd/yy","MM/dd/yyyy"],
              "timezone" : "UTC",
              "separator" : ",",
              "quote" : "\"",
              "encoding" : "utf-8",
              "emptyTextIsNull" : true,
              "trimWhitespace" : true,
              "trimServerWhitespace" : true,
              "overrides" : {}
            }
        }
    -> FeatureWriter_3 [text_line]
Note: Writes control.json
FeatureWriter_3
    DATASET = control.json
    DATASET_ATTR = _dataset
    FEATURE_TYPE_LIST_ATTR = _feature_type
    FORMAT = TEXTLINE
    TEXTLINE_COORDINATE_SYSTEM_GRANULARITY = FEATURE
    TEXTLINE_DESTINATION_DATASETTYPE_VALIDATION = Yes
    TEXTLINE_ENCODING = SYSTEM
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    WRITER_DIRECTIVES = DESTINATION_DATASETTYPE_VALIDATION,Yes,MIME_TYPE,text/plain,END_OF_LINE,System,ENCODING,SYSTEM,WRITE_LAST_EOL,YES,WRITE_UTF8_BOM,YES,OVERWRITE_FILE,YES
    SUMMARY -> FeatureHolder_2
Note: Creates Code to run DataSync in SystemCaller and contents of config.json
AttributeCreator_2
    ATTR_TABLE:
      SET_TO Code = java -jar "$(DataSync_Path)" -c "$(FME_MF_DIR_USERTYPED)config.json" -f "$(FME_MF_DIR_USERTYPED)$(Dataset_ID).csv" -i $(Dataset_ID) -m $(Publish_Method) -ph true -cf "$(FME_MF_DIR_USERTYPED)control.json"
      SET_TO text_line_data = {
            "domain": "$(Domain)",
            "username": "$(Username)",
            "password": "$(Password)",
            "appToken": "$(appToken)"
        }
    -> FeatureWriter_2 [text_line]
    -> FeatureHolder_2
Note: Writes config.json file that has authentication for DataSync
FeatureWriter_2
    DATASET = config.json
    DATASET_ATTR = _dataset
    FEATURE_TYPE_LIST_ATTR = _feature_type
    FORMAT = TEXTLINE
    TEXTLINE_DESTINATION_DATASETTYPE_VALIDATION = Yes
    TEXTLINE_ENCODING = SYSTEM
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    WRITER_DIRECTIVES = DESTINATION_DATASETTYPE_VALIDATION,Yes,MIME_TYPE,text/plain,END_OF_LINE,System,ENCODING,SYSTEM,WRITE_LAST_EOL,YES,WRITE_UTF8_BOM,YES,OVERWRITE_FILE,YES
    SUMMARY -> FeatureHolder_2
Note: Used to wait until .json files are written before triggering SystemCaller
FeatureHolder_2
    -> SystemCaller
Note: Calls and runs DataSync
SystemCaller
    ATTR = Success
    CMD = @Value(Code)
    -> AttributeCreator_3
Note: Creates attribute 'filepath' to point PythonCaller to config.json
AttributeCreator_3
    ATTR_TABLE = SET_TO filepath = $(FME_MF_DIR_USERTYPED)config.json
    -> PythonCaller
Note: Deletes config.json which contains DataSync credentials
PythonCaller
    PYTHONSOURCE:
      import os
      def removeFile(feature):
          file = feature.getAttribute('filepath')
          if os.path.exists(file):
              os.remove(file)
    PYTHONSYMBOL = removeFile

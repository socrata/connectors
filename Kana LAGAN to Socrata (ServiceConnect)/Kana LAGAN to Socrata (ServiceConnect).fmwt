FME workspace Kana LAGAN to Socrata (ServiceConnect).fmwt
Title: kana_lagan_to_socrata_v1
Description: Demonstrates how to pull 311 data from the Kana LAGAN reporting server and push it to a Socrata dataset with a schema suitable to power the ServiceConnect / 311 Explorer application.

Parameters:
- SourceDataset_MSSQL_ADO = LaganPDM   # Source Microsoft SQL Server Non-spatial Name
- DestDataset_SOCRATA = data.nola.gov   # Host

Readers:
- MSSQL_ADO_1: MSSQL_ADO from $(SourceDataset_MSSQL_ADO)

Writers:
- SOCRATA_1: SOCRATA to $(DestDataset_SOCRATA)

dbo.nola_case_view_total (reader MSSQL_ADO_1)
    attributes: CASE_ENQUIRY_ID numeric(18,0), CASE_REFERENCE varchar(50), CREATED_BY_ID varchar(100), OPEN_DT datetime, CLOSED_DT datetime, SLA_TARGET_DT datetime, SLA_SUSPENDED_DT datetime, PRIORITY numeric(6,0), SEVERITY numeric(6,0), CASE_STATUS varchar(50), CLOSURE_REASON varchar(4000), CLOSURE_DESCRIPTION varchar(4000), CLOSED_BY_ID varchar(100), CASE_DESCRIPTION varchar(4000), CASE_TITLE varchar(200), SUBJECT varchar(50), REASON varchar(50), TYPE varchar(50), QUEUE varchar(100), CASE_X numeric(31,11), CASE_Y numeric(31,11), OBJECT_DESCRIPTION varchar(255), OBJECT_TYPE varchar(50), LOCATION_COUNCIL_DISTRICT varchar(80), LOCATION_FIRE_DISTRICT varchar(80), LOCATION_GARBAGE_COLLECTION_DAYS varchar(80), LOCATION_COLLECTION_HAULER varchar(80), LOCATION_STREETLIGHT_ZONE varchar(80), LOCATION_NEIGHBORHOOD varchar(80), LOCATION_POLICE_DISTRICT varchar(80),
      LOCATION_STREET_NUMBER varchar(202), LOCATION_STREET_NAME varchar(100), LOCATION_STREET_NAME2 varchar(100), LOCATION_CITY varchar(100), LOCATION_STATE varchar(2), LOCATION_ZIPCODE varchar(10), LOCATION_X varchar(50), LOCATION_Y varchar(50), CHANNEL_TYPE varchar(50), REPORTER_FIRST_NAME varchar(35), REPORTER_LAST_NAME varchar(255), REPORTER_ADDRESSNUM varchar(202), REPORTER_ADDRESSLINE1 varchar(100), REPORTER_ADDRESSLINE2 varchar(100), REPORTER_CITY varchar(100), REPORTER_STATE varchar(2), REPORTER_ZIPCODE varchar(10), REPORTER_PHONE_NUMBER varchar(35), REPORTER_PHONE_TYPE varchar(25), REPORTER_EMAIL_ADDRESS varchar(255), REPORTER_EMAIL_TYPE varchar(25)
    -> Tester
Tester
    TEST_MODE = Automatic
    TEST_DESCRIPTION = ""
    BOOL_OP = AND
    TEST_CLAUSE:
      TEST @Value(LOCATION_X) != Unknown
      TEST @Value(LOCATION_Y) != Unknown
      TEST @Value(LOCATION_X) != ""
    PASSED -> AttributeReprojector
AttributeReprojector
    XATTR = LOCATION_X
    YATTR = LOCATION_Y
    DEST = EPSG:4326
    SOURCE = LA83-SF-MOD
    -> AttributeValueMapper
AttributeValueMapper
    DIRECTION = Forward (Source To Destination)
    VAL_ATTR = _looked_up
    LUT = FME_NULL_VALUE,0
    SRC = LOCATION_X
    -> StringConcatenator
StringConcatenator
    PARM_LINE = (@Value(LOCATION_Y), @Value(LOCATION_X))
    VAL_ATTR = location
    -> 3iz8-nghx (writer SOCRATA_1)
3iz8-nghx (writer SOCRATA_1)
    attributes: ticket_id text, secondary_issue_type text, issue_type text, ticket_created_date_time date, ticket_closed_date_time date, ticket_status text, issue_description text, street_address text, neighborhood_district text, city text, state text, zip_code number, image text, location location, council_district location

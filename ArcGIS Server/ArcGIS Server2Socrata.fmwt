FME workspace ArcGIS Server2Socrata.fmwt
Title: ArcGIS Server2Socrata
Description: 2nd iteration of ArcGIS Server Socrata Connector
Usage: # ArcGIS Server to Socrata
This example workflow extracts data from ArcGIS Server and pushes it to Socrata.
## Steps to get your JSON URL
1. Determine what ArcGIS layer you want to export
- It must be a Feature Layer with the REST service enabled
- Currently it must be point data. The Socrata writer will coerce all the incoming features down to points by default.
If you want more control over the placement of points you must summarize it down to centroids or something similar 
with a CenterOfGravityReplacer or an InsidePointReplacer.
2. Click on "Query" at the bottom of the layer's entry in the ArcGIS Services Directory. Ex. https://gisrevprxy.seattle.gov/ArcGIS/rest/services/ext/WM_CityGISLayers/MapServer/33
3. Under "Where" enter "1=1" (or whatever more specific query you want for your export)
4. Under "Format" select "JSON"
5. If you want all the feature service attributes be sure to add '*' to the Output Fields. The Esri Json reader will pick these up
automatically
6. Click the "Query (GET)" button
Then copy the URL for your browser's URL bar
Requirements: Socrata account and associated user name & password

Parameters:
- SourceDataset_ESRIJSON = $(FME_MF_DIR)1/3/query?where=1%3D1&text=&objectIds=&time=&geometry=&geometryType=esriGeometryEnvelope&inSR=&spatialRel=esriSpatialRelIntersects&relationParam=&outFields=*&returnGeometry=true&maxAllowableOffset=&geometryPrecision=&outSR=&returnIdsOnly=false&returnCountOnly=false&orderByFields=&groupByFieldsForStatistics=&outStatistics=&returnZ=false&returnM=false&gdbVersion=&returnDistinctValues=false&f=pjson   # Source Esri-JSON File or URL
- DestDataset_SOCRATA = soda.demo.socrata.com   # Host

Readers:
- ESRIJSON_1: ESRIJSON from $(SourceDataset_ESRIJSON)

Writers:
- SOCRATA_1: SOCRATA to $(DestDataset_SOCRATA)

ESRIJSON (reader ESRIJSON_1)
    attributes: OBJECTID int, Submission_Identifier string, LandUse string, FeatureType string, Prvd string, ShrAgt string, ADM1_NAME string, ADM2_NAME string, PhID string, Photos string, Xcoord float, Ycoord float, Bank_Operational string, Bank_Registered string
    -> GeometryFilter
Note: Filter out non-point features
GeometryFilter
    GEOM_PORT_NAMES = Point
    BREAK_AGG = No
    <UNFILTERED> -> Invalid_Feature_Logger
    POINT -> Reprojector_2
Note: The writer will reproject to EPSG:4326 by default, / this ensures features are in the correct projection / before entering the writer.
Reprojector_2
    DEST = LL-WGS84
    RASTER_CELL_SIZE = Preserve Cells
    STROKE_ARCS = Yes
    SOURCE = Read from feature
    INTERPOLATION_TYPE_NAME = Nearest Neighbor
    REPROJECTED -> New Dataset (writer SOCRATA_1)
New Dataset (writer SOCRATA_1)
Note: Generate a friendly error log / when a non-point feature enteres the pipeline
Invalid_Feature_Logger: Logger
    MESSAGE = The Socrata Writer only supports point features.
    MAXFEATS = 20
    MAXCOORDS = 20
    LOGGED -> Terminator
Note: If a non-point feature enters the / workflow then terminate
Terminator
    MESSAGE = Translation Terminated

Bookmark: Esri JSON Reader
Note: The Esri JSON Reader / 1. Determine what ArcGIS layer you want to export / - It must be a Feature Layer with the REST service enabled / - Currently it must be point data. The Socrata writer will coerce all the incoming features down to points by default. If you want more control over the placement of points you must summarize it down to centroids or something similar / with a CenterOfGravityReplacer or an InsidePointReplacer. / In the ESRI Rest Web Interface: / 2. Click on "Query" at the bottom of the layer's entry in the ArcGIS Services Directory. Ex. https://gisrevprxy.seattle.gov/ArcGIS/rest/services/ext/WM_CityGISLayers/MapServer/33 / 3. Under "Where" enter "1=1" (or whatever more specific query you want for your export) / 4. Under "Format" select "JSON" / 5. If you want all the feature service attributes be sure to add '*' to the Output Fields. The Esri Json reader will pick these up automatically / 6. Click the "Query (GET)" button / 7. Copy the URL in the browser and use that as the source for the JSON reader.

Bookmark: Socrata Writer
Note: The Socrata Writer needs the following parameters / - Socrata User Name (usually in the form of an email / - Socrata Password / - Data Set. Try: soda.demo.socrata.com / Be sure to copy the attributes from the data source in order to have the fields in Socrata / Geometry features will populate a location column in Socrata

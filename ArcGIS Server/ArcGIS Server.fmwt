FME workspace ArcGIS Server.fmwt
Title: ArcGIS Server

Parameters:
- SourceDataset_ESRIJSON = $(FME_MF_DIR)1/33/query?text=&geometry=&geometryType=esriGeometryPoint&inSR=&spatialRel=esriSpatialRelIntersects&relationParam=&objectIds=&where=1=1&time=&returnCountOnly=false&returnIdsOnly=false&returnGeometry=true&maxAllowableOffset=&outSR=&outFields=&f=pjson   # Source Esri-JSON File or URL
- socrata_username =   # Socrata Username
- socrata_password =   # Socrata Password
- socrata_app_token = nUDmWszBG05TG2Z1OingWe65A   # Socrata App Token
- socrata_batch_size = 1000   # Request Batch Size
- socrata_dataset_uid =   # Dataset UID

Readers:
- ESRIJSON_1: ESRIJSON from $(SourceDataset_ESRIJSON)

Note: Extract data from ESRI JSON output
ESRIJSON (reader ESRIJSON_1)
    attributes: SCINAME string
    -> AttributeRenamer
Note: Rename our attribute
AttributeRenamer
    ATTR_LIST = SCINAME,scientific_name,""
    -> Reprojector
Note: Reproject into LL-WGS84
Reprojector
    DEST = LL-WGS84
    RASTER_CELL_SIZE = Preserve Cells
    STROKE_ARCS = Yes
    SOURCE = Read from feature
    INTERPOLATION_TYPE_NAME = Nearest Neighbor
    REPROJECTED -> SocrataWriter_v0.3
SocrataWriter_v0.3: PythonCaller
    PYTHONSOURCE:
      import fmeobjects
      import json
      import urllib2
      import base64

      class SocrataFeatureProcessor(object):
          def __init__(self):
              # Get config from the environment
              self.username = FME_MacroValues['socrata_username']
              self.password = FME_MacroValues['socrata_password']
              self.app_token = FME_MacroValues['socrata_app_token']
              self.uid = FME_MacroValues['socrata_dataset_uid']
              self.domain = FME_MacroValues['socrata_domain']
              self.batch_size = FME_MacroValues['socrata_batch_size']

              self.logger = fmeobjects.FMELogFile()
              self.records = []

              # Fetch some metadata about the dataset that we'll use later
              response = urllib2.urlopen(urllib2.Request("https://%s/resource/%s.json?$limit=1" % (self.domain, self.uid)))

              columns = json.loads(response.info()["X-SODA2-Fields"])
              datatypes = json.loads(response.info()["X-SODA2-Types"])

              self.schema = {}
              for i in range(len(columns)):
                  if datatypes[i] != "meta_data":
                      self.schema[columns[i]] = datatypes[i]

          def input(self, feature):
              record = {}

              # Find properties for all of our attributes
              for name, datatype in self.schema.iteritems():
                  if datatype == "location":
                      record[name] = {
                          "longitude" : feature.getGeometry().getXYZ()[0],
                          "latitude" : feature.getGeometry().getXYZ()[1]
                      }
                  elif feature.getAttribute(name) != None:
                      record[name] = feature.getAttribute(name)

              self.records.append(record)

              if len(self.records) >= int(self.batch_size):
                  self.logger.logMessageString("Writing batch of size %d" % len(self.records))
                  self.write()
                  self.records = []

          def write(self):
              # Write this batch out
              payload = json.dumps(self.records) + " \n"
              headers = {
                  "X-App-Token" : self.app_token,
                  "Authorization" : "Basic %s" % base64.encodestring("%s:%s" % (self.username, self.password)).replace('\n', ''),
                  "Content-Type" : "application/json",
                  "Content-Length" : len(payload)
              }

              try:
                  request = urllib2.Request("https://%s/resource/%s.json" % (self.domain, self.uid), data = payload, headers = headers)
                  response = urllib2.urlopen(request)
                  self.logger.logMessageString("Results: %s" % response.read())
              except urllib2.HTTPError as e:
                  # TODO: Smart error handling and stuff
                  self.logger.logMessageString("Code: %s" % e.code)
                  self.logger.logMessageString("Error: %s" % e.read())



          def close(self):
              self.logger.logMessageString("Writing final batch of size %d" % len(self.records))
              self.write()
              self.logger.logMessageString("Done.")
    PYTHONSYMBOL = SocrataFeatureProcessor
